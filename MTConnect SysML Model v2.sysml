library package Profile {
    package DataTypes {
        enum def CoordinateSystemEnum {
            MACHINE {
                doc /* unchangeable coordinate system that has machine zero as its origin.*/
            }
            WORK {
                doc 
                /* coordinate system that represents the working area for a particular workpiece whose origin is shifted within the `MACHINE` coordinate system.
                 *
                 * If the `WORK` coordinates are not currently defined in the piece of equipment, the `MACHINE` coordinates will be used.*/
            }
        }
        enum def ResetTriggerEnum {
            ACTION_COMPLETE {
                doc /* {{term(observation)}} of the {{block(DataItem)}} that is measuring an action or operation is to be reset upon completion of that action or operation.*/
            }
            ANNUAL {
                doc /* {{term(observation)}} of the {{block(DataItem)}} is to be reset at the end of a 12-month period.*/
            }
            DAY {
                doc /* {{term(observation)}} of the {{block(DataItem)}} is to be reset at the end of a 24-hour period.*/
            }
            LIFE {
                doc /* {{term(observation)}} of the {{block(DataItem)}} is not reset and accumulates for the entire life of the piece of equipment.*/
            }
            MAINTENANCE {
                doc /* {{term(observation)}} of the {{block(DataItem)}} is to be reset upon completion of a maintenance event.*/
            }
            MONTH {
                doc /* {{term(observation)}} of the {{block(DataItem)}} is to be reset at the end of a monthly period.*/
            }
            POWER_ON {
                doc /* {{term(observation)}} of the {{block(DataItem)}} is to be reset when power was applied to the piece of equipment after a planned or unplanned interruption of power has occurred.*/
            }
            SHIFT {
                doc /* {{term(observation)}} of the {{block(DataItem)}} is to be reset at the end of a work shift.*/
            }
            WEEK {
                doc /* {{term(observation)}} of the {{block(DataItem)}} is to be reset at the end of a 7-day period.*/
            }
        }
        enum def StatisticEnum {
            AVERAGE {
                doc /* mathematical average value calculated for the data item during the calculation period.*/
            }
            KURTOSIS {
                doc /* **DEPRECATED** in *Version 1.6*. ~~A measure of the "peakedness" of a probability distribution; i.e., the shape of the distribution curve.~~*/
            }
            MAXIMUM {
                doc /* maximum or peak value recorded for the data item during the calculation period.*/
            }
            MEDIAN {
                doc /* middle number of a series of numbers.*/
            }
            MINIMUM {
                doc /* minimum value recorded for the data item during the calculation period.*/
            }
            MODE {
                doc /* number in a series of numbers that occurs most often.*/
            }
            RANGE {
                doc /* difference between the maximum and minimum value of a data item during the calculation period. Also represents Peak-to-Peak measurement in a waveform.*/
            }
            ROOT_MEAN_SQUARE {
                doc /* mathematical Root Mean Square (RMS) value calculated for the data item during the calculation period.*/
            }
            STANDARD_DEVIATION {
                doc /* statistical Standard Deviation value calculated for the data item during the calculation period.*/
            }
        }
        enum def UnitEnum {
            AMPERE {
                doc /* electric current in ampere.*/
            }
            CELSIUS {
                doc /* temperature in degree Celsius.*/
            }
            COUNT {
                doc /* count of something.*/
            }
            DECIBEL {
                doc /* sound level in decibel.*/
            }
            DEGREE {
                doc /* angle in degree.*/
            }
            DEGREE_3D {
                doc 
                /* space-delimited, floating-point representation of the angular rotation in degrees around the X, Y, and Z axes relative to a cartesian coordinate system respectively in order as A, B, and C. 
                 *
                 * If any of the rotations is not known, it **MUST** be zero (0).*/
            }
            'DEGREE/SECOND' {
                doc /* angular velocity in degree per second.*/
            }
            'DEGREE/SECOND^2' {
                doc /* angular acceleration in degree per second squared.*/
            }
            HERTZ {
                doc /* frequency in cycles per second.*/
            }
            JOULE {
                doc /* energy in joule.*/
            }
            KILOGRAM {
                doc /* mass in kilogram.*/
            }
            LITER {
                doc /* volume in liter.*/
            }
            'LITER/SECOND' {
                doc /* volumetric flow in liter per second.*/
            }
            MICRO_RADIAN {
                doc /* tilt in micro radian.*/
            }
            MILLIMETER {
                doc /* length in millimeter.*/
            }
            MILLIMETER_3D {
                doc /* point in space identified by X, Y, and Z positions and represented by a space-delimited set of numbers each expressed in millimeters.*/
            }
            'MILLIMETER/REVOLUTION' {
                doc /* feedrate per revolution in millimeter per revolution.*/
            }
            'MILLIMETER/SECOND' {
                doc /* speed in millimeter per second.*/
            }
            'MILLIMETER/SECOND^2' {
                doc /* acceleration in millimeter per second squared.*/
            }
            NEWTON {
                doc /* force in newton.*/
            }
            NEWTON_METER {
                doc /* torque in newton-meter.*/
            }
            OHM {
                doc /* electrical resistance in ohm.*/
            }
            PASCAL {
                doc /* pressure or stress in pascal.*/
            }
            PASCAL_SECOND {
                doc /* viscosity in pascal-second.*/
            }
            PERCENT {
                doc /* amount in or for every hundred.*/
            }
            PH {
                doc /* acidity or alkalinity of a solution in pH.*/
            }
            'REVOLUTION/MINUTE' {
                doc /* rotational velocity in revolution per minute.*/
            }
            SECOND {
                doc /* time in second.*/
            }
            'SIEMENS/METER' {
                doc /* electrical conductivity in siemens per meter.*/
            }
            VOLT {
                doc /* electric potential, electric potential difference or electromotive force in volt.*/
            }
            VOLT_AMPERE {
                doc /* apparent power in an electrical circuit, equal to the product of root-mean-square (RMS) voltage and RMS current (commonly referred to as VA) in volt-ampere.*/
            }
            VOLT_AMPERE_REACTIVE {
                doc /* reactive power in an AC electrical circuit (commonly referred to as VAR) in volt-ampere-reactive.*/
            }
            WATT {
                doc /* power in watt.*/
            }
            WATT_SECOND {
                doc /* electrical energy in watt-second*/
            }
            'GRAM/CUBIC_METER' {
                doc /* density in gram per cubic meter.*/
            }
            CUBIC_MILLIMETER {
                doc /* geometric volume in millimeter.*/
            }
            'CUBIC_MILLIMETER/SECOND' {
                doc /* change of geometric volume per second.*/
            }
            'CUBIC_MILLIMETER/SECOND^2' {
                doc /* change in geometric volume per second squared.*/
            }
            MILLIGRAM {
                doc /* mass in milligram.*/
            }
            'MILLIGRAM/CUBIC_MILLIMETER' {
                doc /* density in milligram per cubic millimeter.*/
            }
            MILLILITER {
                doc /* volume in milliliter.*/
            }
            'COUNT/SECOND' {
                doc /* frequency in count per second.*/
            }
            'PASCAL/SECOND' {
                doc /* pressurization rate in pascal per second.*/
            }
            UNIT_VECTOR_3D {
                doc 
                /* 3D Unit Vector.
                 *
                 * Space delimited list of three floating point numbers.*/
            }
            'REVOLUTION/SECOND^2' {
                doc /* rotational acceleration in revolution per second squared.*/
            }
            'REVOLUTION/SECOND' {
                doc /* rotational velocity in revolution per second.*/
            }
            GRAM {
                doc /* mass in gram.*/
            }
            'METER/SECOND^2' {
                doc /* acceleration in meter per second squared.*/
            }
            COULOMB {
                doc /* electric charge in coulomb.*/
            }
            CUBIC_METER {
                doc /* geometric volume in meter.*/
            }
            SQUARE_MILLIMETER {
                doc /* geometric area in millimeter.*/
            }
            OHM_METER {
                doc /* resistivity in ohm-meter.*/
            }
            'MILLIGRAM/LITER' {
                doc /* concentration of a dissolved substance in milligram per liter*/
            }
        }
        enum def DataItemTypeEnum;
        enum def CategoryEnum {
            SAMPLE {
                doc 
                /* continuously variable or analog data value. 
                 *
                 * A continuous value can be measured at any point-in-time and will always produce a result.*/
            }
            EVENT {
                doc /* discrete piece of information from the piece of equipment.*/
            }
            CONDITION {
                doc /* information about the health of a piece of equipment and its ability to function.*/
            }
        }
        enum def DataItemSubTypeEnum {
            ABSOLUTE {
                doc /* relating to or derived in the simplest manner from the fundamental units or measurements.*/
            }
            ACTION {
                doc /* indication of the operating state of a mechanism.*/
            }
            ACTUAL {
                doc /* reported value of an {{term(observation)}}.*/
            }
            ALL {
                doc /* all actions, items, or activities being counted independent of the outcome.*/
            }
            ALTERNATING {
                doc 
                /* measurement of alternating voltage or current. If not specified further in statistic, defaults to RMS voltage. 
                 *
                 * **DEPRECATED** in *Version 1.6*.*/
            }
            A_SCALE {
                doc /* A-Scale weighting factor on the frequency scale.*/
            }
            AUXILIARY {
                doc /* when multiple locations on a piece of bar stock being feed by a bar feeder are referenced as the indication of whether the end of that piece of bar stock has been reached.*/
            }
            BAD {
                doc /* actions, items, or activities being counted that do not conform to specification or expectation.*/
            }
            BRINELL {
                doc /* scale to measure the resistance to deformation of a surface.*/
            }
            B_SCALE {
                doc /* B-Scale weighting factor on the frequency scale.*/
            }
            COMMANDED {
                doc /* directive value including adjustments such as an offset or overrides.*/
            }
            CONSUMED {
                doc /* amount of material consumed from an object or container during a manufacturing process.*/
            }
            CONTROL {
                doc /* state of the enabling signal or control logic that enables or disables the function or operation of the entity.*/
            }
            C_SCALE {
                doc /* C-Scale weighting factor on the frequency scale.*/
            }
            DELAY {
                doc /* elapsed time of a temporary halt of action.*/
            }
            DIRECT {
                doc 
                /* DC current or voltage.
                 *
                 * **DEPRECATED** in *Version 1.6*.*/
            }
            DRY_RUN {
                doc /* setting or operator selection used to execute a test mode to confirm the execution of machine functions.*/
            }
            D_SCALE {
                doc /* D-Scale weighting factor on the frequency scale.*/
            }
            EXPIRATION {
                doc /* relating to the expiration or end of useful life for a material or other physical item.*/
            }
            FIRST_USE {
                doc /* relating to the first use of a material or other physical item.*/
            }
            GOOD {
                doc /* actions, items, or activities being counted that conform to specification or expectation.*/
            }
            INCREMENTAL {
                doc /* relating to or derived from the last {{term(observation)}}.*/
            }
            JOG {
                doc 
                /* relating to momentary activation of a function or a movement.
                 *
                 * **DEPRECATION WARNING**: May be deprecated in the future.*/
            }
            LATERAL {
                doc /* indication of the position of a mechanism that may move in a lateral direction.*/
            }
            LEEB {
                doc /* scale to measure the elasticity of a surface.*/
            }
            LENGTH {
                doc /* reference to a length type tool offset variable.*/
            }
            LINE {
                doc /* state of the power source.*/
            }
            LINEAR {
                doc /* direction of motion of a linear motion.*/
            }
            LOADED {
                doc /* indication that the subparts of a piece of equipment are under load.*/
            }
            MACHINE_AXIS_LOCK {
                doc /* setting or operator selection that changes the behavior of the controller on a piece of equipment.*/
            }
            MAIN {
                doc /* relating to the primary logic or motion program currently being executed.*/
            }
            MAINTENANCE {
                doc /* relating to maintenance on the piece of equipment.*/
            }
            MANUAL_UNCLAMP {
                doc /* indication of the state of an operator controlled interlock that can inhibit the ability to initiate an unclamp action of an electronically controlled chuck.*/
            }
            MANUFACTURE {
                doc /* related to the production of a material or other physical item.*/
            }
            MAXIMUM {
                doc /* maximum value.*/
            }
            MINIMUM {
                doc /* minimum value.*/
            }
            MOHS {
                doc /* scale to measure the resistance to scratching of a surface.*/
            }
            MOTION {
                doc /* indication of the open or closed state of a mechanism.*/
            }
            NO_SCALE {
                doc /* no weighting factor on the frequency scale.*/
            }
            OPERATING {
                doc /* piece of equipment that is powered or performing any activity.*/
            }
            OPERATOR {
                doc /* relating to the person currently responsible for operating the piece of equipment.*/
            }
            OPTIONAL_STOP {
                doc /* setting or operator selection that changes the behavior of the controller on a piece of equipment. */
            }
            OVERRIDE {
                doc /* overridden value.*/
            }
            POWERED {
                doc /* piece of equipment is powered and functioning or {{block(Component)}} that are required to remain on are powered.*/
            }
            PRIMARY {
                doc /* main or principle.*/
            }
            PROBE {
                doc 
                /* position provided by a measurement probe.
                 *
                 * **DEPRECATION WARNING**: May be deprecated in the future.*/
            }
            PROCESS {
                doc /* relating to production of a part or product on a piece of equipment.*/
            }
            PROGRAMMED {
                doc /* directive value without offsets and adjustments.*/
            }
            RADIAL {
                doc /* reference to a radial type tool offset variable.*/
            }
            RAPID {
                doc /* performing an operation faster or in less time than nominal rate.*/
            }
            REMAINING {
                doc /* remaining measure or count of an action, object or activity.*/
            }
            ROCKWELL {
                doc /* scale to measure the resistance to deformation of a surface.*/
            }
            ROTARY {
                doc /* direction of a rotary motion using the right hand rule convention.*/
            }
            SCHEDULE {
                doc /* identity of a control program that is used to specify the order of execution of other programs.*/
            }
            SET_UP {
                doc /* relating to the preparation of a piece of equipment for production or restoring the piece of equipment to a neutral state after production.*/
            }
            SHORE {
                doc /* scale to measure the resistance to deformation of a surface.*/
            }
            SINGLE_BLOCK {
                doc /* setting or operator selection that changes the behavior of the controller on a piece of equipment. */
            }
            STANDARD {
                doc /* standard measure of an object or an action.*/
            }
            START {
                doc /* boundary when an activity or an event commences.*/
            }
            SWITCHED {
                doc /* indication of the activation state of a mechanism represented by a {{block(Composition)}}.*/
            }
            TARGET {
                doc /* goal of the operation or process.*/
            }
            TARGET_COMPLETION {
                doc /* relating to the end or completion of an activity or event.*/
            }
            TOOL_CHANGE_STOP {
                doc /* setting or operator selection that changes the behavior of the controller on a piece of equipment.*/
            }
            USEABLE {
                doc /* remaining usable measure of an object or action.*/
            }
            VERTICAL {
                doc /* indication of the position of a mechanism that may move in a vertical direction.*/
            }
            VICKERS {
                doc /* scale to measure the resistance to deformation of a surface.*/
            }
            WORKING {
                doc /* piece of equipment performing any activity, the equipment is active and performing a function under load or not.*/
            }
            IPV4_ADDRESS {
                doc /* IPV4 network address of the {{block(Component)}}.*/
            }
            IPV6_ADDRESS {
                doc /* IPV6 network address of the {{block(Component)}}.*/
            }
            GATEWAY {
                doc /* Gateway for the {{block(Component)}} network.*/
            }
            SUBNET_MASK {
                doc /* SubNet mask for the {{block(Component)}} network.*/
            }
            VLAN_ID {
                doc /* layer2 Virtual Local Network (VLAN) ID for the {{block(Component)}} network.*/
            }
            MAC_ADDRESS {
                doc /* Media Access Control Address. The unique physical address of the network hardware.*/
            }
            WIRELESS {
                doc /* identifies whether the connection type is wireless.*/
            }
            LICENSE {
                doc /* license code to validate or activate the hardware or software.*/
            }
            VERSION {
                doc /* version of the hardware or software.*/
            }
            RELEASE_DATE {
                doc /* date the hardware or software was released for general use.*/
            }
            INSTALL_DATE {
                doc /* date the hardware or software was installed.*/
            }
            MANUFACTURER {
                doc /* corporate identity for the maker of the hardware or software.*/
            }
            UUID {
                doc /* universally unique identifier as specified in ISO 11578 or RFC 4122.*/
            }
            SERIAL_NUMBER {
                doc /* serial number that uniquely identifies a specific part.*/
            }
            RAW_MATERIAL {
                doc /* material that is used to produce parts.*/
            }
            LOT {
                doc /* group of parts tracked as a lot.*/
            }
            BATCH {
                doc /* group of parts produced in a batch.*/
            }
            HEAT_TREAT {
                doc /* material heat number.*/
            }
            PART_NUMBER {
                doc /* particular part design or model.*/
            }
            PART_FAMILY {
                doc /* group of parts having similarities in geometry, manufacturing process, and/or functions.*/
            }
            PART_NAME {
                doc /* word or set of words by which a part is known, addressed, or referred to.*/
            }
            PROCESS_STEP {
                doc /* step in the process plan that this occurrence corresponds to. */
            }
            PROCESS_PLAN {
                doc /* process plan that a process occurrence belongs to.*/
            }
            ORDER_NUMBER {
                doc /* authorization of a process occurrence.*/
            }
            PROCESS_NAME {
                doc /* word or set of words by which a process being executed (process occurrence) by the device is known, addressed, or referred to.*/
            }
            ISO_STEP_EXECUTABLE {
                doc /* reference to a ISO 10303 Executable.*/
            }
            COMPLETE {
                doc /* associated with the completion of an activity or event.*/
            }
            ACTIVE {
                doc /* relating to logic or motion program currently executing.*/
            }
            FAILED {
                doc /* actions or activities that were attempted , but failed to complete or resulted in an unexpected or unacceptable outcome.*/
            }
            ABORTED {
                doc /* actions or activities that were attempted, but terminated before they could be completed.*/
            }
            ENDED {
                doc /* boundary when an activity or an event terminates.*/
            }
            WASTE {
                doc /* amount discarded.*/
            }
            PART {
                doc /* amount included in the {{term(part)}}.*/
            }
            REQUEST {
                doc /* {{term(request)}} by an {{block(Interface)}} for a task.*/
            }
            RESPONSE {
                doc /* {{term(response)}} by an {{block(Interface)}} to a {{term(request)}} for a task.*/
            }
            ACTIVITY {
                doc /* phase or segment of a recipe or program.*/
            }
            SEGMENT {
                doc /* phase of a recipe process.*/
            }
            RECIPE {
                doc /* process as part of product production; can be a subprocess of a larger process.*/
            }
            OPERATION {
                doc /* step of a discrete manufacturing process.*/
            }
            BINARY {
                doc /* observed as a binary data type.*/
            }
            BOOLEAN {
                doc /* observed as a boolean data type.*/
            }
            ENUMERATED {
                doc 
                /* observed as a set containing a restricted number of discrete values where each discrete value is named and unique.
                 * {{cite(ISO 21961:2003, 013)}}*/
            }
            DETECT {
                doc /* indicated by the presence or existence of something.*/
            }
            MODEL {
                doc /* model info of the hardware or software.*/
            }
            MEASURED {
                doc /* {{def(DataItemSubType::ACTUAL)}} that has {{term(uncertainty)}}.*/
            }
            GAS {
                doc /* fluid that has no definite shape or volume.*/
            }
            LIQUID {
                doc /* fluid that has a definite volume but no definite shape.*/
            }
            SOLID {
                doc /* matter that has a definite shape and a definite volume.*/
            }
            ELECTRODE {
                doc /* component used for many electrical discharge manufacturing processes like welding*/
            }
            FILLER {
                doc /* material used to fill a gap or space*/
            }
            PLUNGE {
                doc /* move with a rush or sudden impulse into or out of*/
            }
            PECK {
                doc /* move suddenly or in a jerking motion*/
            }
            CUT {
                doc /* engagement of a tool edge in material*/
            }
            LAYER {
                doc /* sheet, quantity, or thickness of material, typically one of several, covering a surface or body*/
            }
        }
        enum def NativeUnitEnum :> UnitEnum {
            CENTIPOISE {
                doc /* viscosity in centipoise.*/
            }
            'DEGREE/MINUTE' {
                doc /* rotational velocity in degree per minute.*/
            }
            FAHRENHEIT {
                doc /* temperature in Fahrenheit.*/
            }
            FOOT {
                doc /* length in foot.*/
            }
            'FOOT/MINUTE' {
                doc /* speed in foot per minute.*/
            }
            'FOOT/SECOND' {
                doc /* speed in foot per second.*/
            }
            'FOOT/SECOND^2' {
                doc /* acceleration in foot per second squared.*/
            }
            FOOT_3D {
                doc /* point in space identified by X, Y, and Z positions and represented by a space-delimited set of numbers each expressed in feet.*/
            }
            'GALLON/MINUTE' {
                doc /* volumetric flow in gallon per minute.*/
            }
            HOUR {
                doc /* time in hour.*/
            }
            INCH {
                doc /* length in inch.*/
            }
            'INCH/MINUTE' {
                doc /* speed in inch per minute.*/
            }
            'INCH/SECOND' {
                doc /* speed in inch per second.*/
            }
            'INCH/SECOND^2' {
                doc /* acceleration in inch per second squared.*/
            }
            INCH_POUND {
                doc /* torque in inch pound.*/
            }
            INCH_3D {
                doc /* point in space identified by X, Y, and Z positions and represented by a space-delimited set of numbers each expressed in inches.*/
            }
            KELVIN {
                doc /* temperature in Kelvin.*/
            }
            KILOWATT {
                doc /* power in kilowatt.*/
            }
            KILOWATT_HOUR {
                doc /* energy in kilowatt-hour.*/
            }
            'LITER/MINUTE' {
                doc /* volumetric flow in liter per minute.*/
            }
            'MILLIMETER/MINUTE' {
                doc /* speed in millimeter per minute.*/
            }
            MINUTE {
                doc /* time in minute.*/
            }
            OTHER {
                doc /* unsupported unit.*/
            }
            POUND {
                doc /* mass in pound.*/
            }
            'POUND/INCH^2' {
                doc /* pressure in pound per square inch (PSI).*/
            }
            RADIAN {
                doc /* angle in radian.*/
            }
            'RADIAN/MINUTE' {
                doc /* angular velocity in radian per minute.*/
            }
            'RADIAN/SECOND' {
                doc /* angular velocity in radian per second.*/
            }
            'RADIAN/SECOND^2' {
                doc /* angular acceleration in radian per second squared.*/
            }
            BAR {
                doc /* pressure in bar.*/
            }
            TORR {
                doc /* pressure in torr.*/
            }
            MILLIMETER_MERCURY {
                doc /* pressure in millimeter of mercury (mmHg).*/
            }
            'PASCAL/MINUTE' {
                doc /* pressurization rate in pascal per minute.*/
            }
            GRAVITATIONAL_FORCE {
                doc /* `MASS` times `GRAVITATIONAL_ACCELERATION`  (g).*/
            }
            GRAVITATIONAL_ACCELERATION {
                doc 
                /* acceleration relative to earth's gravity given in meter per second squared.
                 *
                 * > Note 1 to entry: At different points on Earth's surface, the free-fall acceleration ranges from 9.764 to 9.834 m/s2 (Wikipedia: Gravitational Acceleration). The constant can be customized depending on the location in the universe.
                 *
                 * > Note 2 to entry: In the standard, it is assumed that Earth's average value of gravitational acceleration is 9.90665 m/s2.*/
            }
            AMPERE_HOUR {
                doc /* electric charge in ampere hour.*/
            }
            'CUBIC_FOOT/HOUR' {
                doc /* change of geometric volume in cubic foot per hour.*/
            }
            'CUBIC_FOOT/MINUTE' {
                doc /* change of geometric volume in cubic foot per minute.*/
            }
            SQUARE_INCH {
                doc /* geometric area in inch squared.*/
            }
            CUBIC_FOOT {
                doc /* geometric volume in cubic foot.*/
            }
            'INCH/REVOLUTION' {
                doc /* feedrate per revolution in inch per revolution.*/
            }
            MICROMETER {
                doc /* length in micrometer.*/
            }
            RANKINE {
                doc /* temperature in Rankine.*/
            }
            MICROTORR {
                doc /* pressure in microtorr.*/
            }
        }
        enum def FilterEnum {
            MINIMUM_DELTA {
                doc 
                /* new value **MUST NOT** be reported for a data item unless the measured value has changed from the last reported value by at least the delta given as the value of this element.
                 *
                 * The value of {{block(Filter)}} **MUST** be an absolute value using the same units as the reported data.*/
            }
            PERIOD {
                doc 
                /* data reported for a data item is provided on a periodic basis. The `PERIOD` for reporting data is defined in the value of the {{block(Filter)}}.
                 *
                 * The value of {{block(Filter)}} **MUST** be an absolute value reported in seconds representing the time between reported samples of the value of the data item.*/
            }
        }
        enum def RepresentationEnum {
            TIME_SERIES {
                doc 
                /* series of sampled data.
                 *
                 * The data is reported for a specified number of samples and each sample is reported with a fixed period.*/
            }
            VALUE {
                doc 
                /* measured value of the sample data.
                 *
                 * If no {{property(DataItem::representation)}} is specified for a data item, the {{property(DataItem::representation)}} **MUST** be determined to be `VALUE`.*/
            }
            DATA_SET {
                doc 
                /* reported value(s) are represented as a set of {{termplural(key-value pair)}}.
                 *
                 * Each reported value in the {{term(data set)}} **MUST** have a unique key.*/
            }
            DISCRETE {
                doc /* **DEPRECATED** as {{property(DataItem::representation)}} type in *MTConnect Version 1.5*. Replaced by the {{property(DataItem::discrete)}}.*/
            }
            TABLE {
                doc 
                /* two dimensional set of {{termplural(key-value pair)}} where the {{block(Entry)}} represents a row, and the value is a set of {{term(key-value pair)}} {{block(Cell)}} elements. 
                 *
                 * A {{term(table)}} follows the same behavior as the {{term(data set)}} for change tracking, clearing, and history. When an {{block(Entry)}} changes, all {{block(Cell)}} elements update as a single unit following the behavior of a {{term(data set)}}.
                 *
                 * > Note: It is best to use {{block(Variable)}} if the {{block(Cell)}} entities represent multiple semantic types.
                 *
                 * Each {{block(Entry)}} in the {{term(table)}} **MUST** have a unique key. Each {{block(Cell)}} of each {{block(Entry)}} in the {{term(table)}} **MUST** have a unique key.
                 *
                 * See {{block(Representation)}} in {{package(Observation Information Model)}}, for a description of {{block(Entry)}} and {{block(Cell)}} elements.*/
            }
        }
        attribute def boolean :> NOT_COMPATIBLE_WITH_TEXTUAL {
            doc /* primitive type.*/
        }
        attribute def ID :> string {
            doc /* string that represents an {{term(ID)}}.*/
        }
        attribute def string :> NOT_COMPATIBLE_WITH_TEXTUAL {
            doc /* primitive type.*/
        }
        attribute def float :> NOT_COMPATIBLE_WITH_TEXTUAL {
            doc /* primitive type.*/
        }
        attribute def datetime :> string {
            doc /* string that represents timestamp in ISO 8601 format.*/
        }
        attribute def integer :> NOT_COMPATIBLE_WITH_TEXTUAL {
            doc /* primitive type.*/
        }
        attribute def xlinktype :> string {
            doc /* string that represents the type of an XLink element. See {{url(https://www.w3.org/TR/xlink11/)}}.*/
        }
        attribute def xslang :> string {
            doc /* string that represents a language tag. See {{url(http://www.ietf.org/rfc/rfc4646.txt)}}.*/
        }
        attribute def SECOND :> unit {
            doc /* float that represents time in seconds.*/
        }
        attribute def xlinkhref :> string {
            doc /* string that represents the locator attribute of an XLink element. See {{url(https://www.w3.org/TR/xlink11/)}}.*/
        }
        enum def ResetTriggeredEnum {
            ACTION_COMPLETE {
                doc /* {{property(Observation::result)}} is measuring an action or operation was reset upon completion of that action or operation.*/
            }
            ANNUAL {
                doc /* {{property(Observation::result)}} was reset at the end of a 12-month period.*/
            }
            DAY {
                doc /* {{property(Observation::result)}} was reset at the end of a 24-hour period.*/
            }
            MAINTENANCE {
                doc /* {{property(Observation::result)}} was reset upon completion of a maintenance event.*/
            }
            MANUAL {
                doc /* {{property(Observation::result)}} was reset based on a physical reset action.*/
            }
            MONTH {
                doc /* {{property(Observation::result)}} was reset at the end of a monthly period.*/
            }
            POWER_ON {
                doc /* {{property(Observation::result)}} was reset when power was applied to the piece of equipment after a planned or unplanned interruption of power has occurred.*/
            }
            SHIFT {
                doc /* {{property(Observation::result)}} was reset at the end of a work shift.*/
            }
            WEEK {
                doc /* {{property(Observation::result)}} was reset at the end of a 7-day period.*/
            }
        }
        enum def QualifierEnum {
            HIGH {
                doc /* measured value is greater than the expected value for a process variable.*/
            }
            LOW {
                doc /* measured value is less than the expected value for a process variable.*/
            }
        }
        enum def SampleEnum :> DataItemTypeEnum {
            ACCELERATION {
                doc /* positive rate of change of velocity.*/
            }
            ACCUMULATED_TIME {
                doc /* accumulated time for an activity or event.*/
            }
            AMPERAGE {
                doc 
                /* strength of electrical current.
                 *
                 * **DEPRECATED** in *Version 1.6*. Replaced by `AMPERAGE_AC` and `AMPERAGE_DC`.*/
            }
            ANGLE {
                doc /* angular position.*/
            }
            ANGULAR_ACCELERATION {
                doc /* positive rate of change of angular velocity.*/
            }
            ANGULAR_VELOCITY {
                doc /* rate of change of angular position.*/
            }
            AXIS_FEEDRATE {
                doc /* feedrate of a linear axis.*/
            }
            CAPACITY_FLUID {
                doc /* maximum amount of fluid that can be held by a container.*/
            }
            CAPACITY_SPATIAL {
                doc /* maximum amount of material that can be held by a container.*/
            }
            CONCENTRATION {
                doc /* percentage of one component within a mixture of components.*/
            }
            CONDUCTIVITY {
                doc /* ability of a material to conduct electricity.*/
            }
            CUTTING_SPEED {
                doc /* speed difference (relative velocity) between the cutting mechanism and the surface of the workpiece it is operating on.*/
            }
            DENSITY {
                doc /* volumetric mass of a material per unit volume of that material.*/
            }
            DEPOSITION_ACCELERATION_VOLUMETRIC {
                doc /* rate of change in spatial volume of material deposited in an additive manufacturing process.*/
            }
            DEPOSITION_DENSITY {
                doc /* density of the material deposited in an additive manufacturing process per unit of volume.*/
            }
            DEPOSITION_MASS {
                doc /* mass of the material deposited in an additive manufacturing process.*/
            }
            DEPOSITION_RATE_VOLUMETRIC {
                doc /* rate at which a spatial volume of material is deposited in an additive manufacturing process.*/
            }
            DEPOSITION_VOLUME {
                doc /* spatial volume of material to be deposited in an additive manufacturing process.*/
            }
            DISPLACEMENT {
                doc /* change in position of an object.*/
            }
            ELECTRICAL_ENERGY {
                doc /* {{block(Wattage)}} used or generated by a component over an interval of time.*/
            }
            EQUIPMENT_TIMER {
                doc /* amount of time a piece of equipment or a sub-part of a piece of equipment has performed specific activities.*/
            }
            FILL_LEVEL {
                doc /* amount of a substance remaining compared to the planned maximum amount of that substance.*/
            }
            FLOW {
                doc /* rate of flow of a fluid.*/
            }
            FREQUENCY {
                doc /* number of occurrences of a repeating event per unit time.*/
            }
            GLOBAL_POSITION {
                doc 
                /* position in three-dimensional space.
                 *
                 * **DEPRECATED** in Version 1.1.*/
            }
            LENGTH {
                doc /* length of an object.*/
            }
            LEVEL {
                doc 
                /* level of a resource.
                 *
                 * **DEPRECATED** in *Version 1.2*.  See `FILL_LEVEL`.*/
            }
            LINEAR_FORCE {
                doc /* {{term(force)}} applied to a mass in one direction only.*/
            }
            LOAD {
                doc /* actual versus the standard rating of a piece of equipment.*/
            }
            MASS {
                doc /* mass of an object(s) or an amount of material.*/
            }
            PATH_FEEDRATE {
                doc /* feedrate for the axes, or a single axis, associated with a {{block(Path)}} component.*/
            }
            PATH_FEEDRATE_PER_REVOLUTION {
                doc /* feedrate for the axes, or a single axis.*/
            }
            PATH_POSITION {
                doc /* position of a control point associated with a {{block(Controller)}} or a {{block(Path)}}.*/
            }
            PH {
                doc /* acidity or alkalinity of a solution.*/
            }
            POSITION {
                doc /* point along an axis in a {{term(cartesian coordinate system)}}.*/
            }
            POWER_FACTOR {
                doc /* ratio of real power flowing to a load to the apparent power in that AC circuit.*/
            }
            PRESSURE {
                doc 
                /* force per unit area measured relative to atmospheric pressure. 
                 *
                 * Commonly referred to as gauge pressure.*/
            }
            PROCESS_TIMER {
                doc /* amount of time a piece of equipment has performed different types of activities associated with the process being performed at that piece of equipment.*/
            }
            RESISTANCE {
                doc /* degree to which a substance opposes the passage of an electric current.*/
            }
            ROTARY_VELOCITY {
                doc /* rotational speed of a rotary axis.*/
            }
            SOUND_LEVEL {
                doc /* sound level or sound pressure level relative to atmospheric pressure.*/
            }
            SPINDLE_SPEED {
                doc 
                /* rotational speed of the rotary axis.
                 *
                 * **DEPRECATED** in *Version 1.2*.  Replaced by `ROTARY_VELOCITY`.*/
            }
            STRAIN {
                doc /* amount of deformation per unit length of an object when a load is applied.*/
            }
            TEMPERATURE {
                doc /* degree of hotness or coldness measured on a definite scale.*/
            }
            TENSION {
                doc /* force that stretches or elongates an object.*/
            }
            TILT {
                doc /* angular displacement.*/
            }
            TORQUE {
                doc /* turning force exerted on an object or by an object.*/
            }
            VELOCITY {
                doc /* rate of change of position of a {{block(Component)}}.*/
            }
            VISCOSITY {
                doc /* fluid's resistance to flow.*/
            }
            VOLTAGE {
                doc 
                /* electrical potential between two points.
                 *
                 * **DEPRECATED** in *Version 1.6*. Replaced by `VOLTAGE_AC` and `VOLTAGE_DC`.*/
            }
            VOLT_AMPERE {
                doc /* apparent power in an electrical circuit, equal to the product of root-mean-square (RMS) voltage and RMS current (commonly referred to as VA).*/
            }
            VOLT_AMPERE_REACTIVE {
                doc /* reactive power in an AC electrical circuit (commonly referred to as VAR).*/
            }
            VOLUME_FLUID {
                doc /* fluid volume of an object or container.*/
            }
            VOLUME_SPATIAL {
                doc /* geometric volume of an object or container.*/
            }
            WATTAGE {
                doc /* power flowing through or dissipated by an electrical circuit or piece of equipment.*/
            }
            AMPERAGE_AC {
                doc /* electrical current that reverses direction at regular short intervals.*/
            }
            AMPERAGE_DC {
                doc /* electric current flowing in one direction only.*/
            }
            VOLTAGE_AC {
                doc /* electrical potential between two points in an electrical circuit in which the current periodically reverses direction.*/
            }
            VOLTAGE_DC {
                doc /* electrical potential between two points in an electrical circuit in which the current is unidirectional.*/
            }
            X_DIMENSION {
                doc /* dimension of an entity relative to the X direction of the referenced coordinate system.*/
            }
            Y_DIMENSION {
                doc /* dimension of an entity relative to the Y direction of the referenced coordinate system.*/
            }
            Z_DIMENSION {
                doc /* dimension of an entity relative to the Z direction of the referenced coordinate system.*/
            }
            DIAMETER {
                doc /* dimension of a diameter.*/
            }
            ORIENTATION {
                doc /* angular position of a plane or vector relative to a {{term(cartesian coordinate system)}}*/
            }
            HUMIDITY_RELATIVE {
                doc /* amount of water vapor present expressed as a percent to reach saturation at the same temperature.*/
            }
            HUMIDITY_ABSOLUTE {
                doc /* amount of water vapor expressed in grams per cubic meter.*/
            }
            HUMIDITY_SPECIFIC {
                doc /* ratio of the water vapor present over the total weight of the water vapor and air present expressed as a percent.*/
            }
            OBSERVATION_UPDATE_RATE {
                doc /* average rate of change of values for data items in the MTConnect streams. The average is computed over a rolling window defined by the implementation.*/
            }
            ASSET_UPDATE_RATE {
                doc 
                /* average rate of change of values for assets in the MTConnect streams. 
                 *
                 * The average is computed over a rolling window defined by the implementation.*/
            }
            PRESSURIZATION_RATE {
                doc /* change of pressure per unit time.*/
            }
            DECELERATION {
                doc /* negative rate of change of velocity.*/
            }
            ANGULAR_DECELERATION {
                doc /* negative rate of change of angular velocity.*/
            }
            PRESSURE_ABSOLUTE {
                doc /* force per unit area measured relative to a vacuum.*/
            }
            OPENNESS {
                doc /* percentage open where 100% is fully open and 0% is fully closed.*/
            }
            DEW_POINT {
                doc /* temperature at which moisture begins to condense, corresponding to saturation for a given absolute humidity.*/
            }
            GRAVITATIONAL_FORCE {
                doc /* force relative to earth's gravity.*/
            }
            GRAVITATIONAL_ACCELERATION {
                doc /* acceleration relative to Earth's gravity of 9.80665 `METER/SECOND^2`.*/
            }
            BATTERY_CAPACITY {
                doc /* maximum rated charge a battery is capable of maintaining based on the battery discharging at a specified current over a specified time period.*/
            }
            DISCHARGE_RATE {
                doc /* value of current being drawn from the {{block(Component)}}.*/
            }
            CHARGE_RATE {
                doc /* value of the current being supplied to the {{block(Component)}} for the purpose of charging.*/
            }
            BATTERY_CHARGE {
                doc /* value of the battery's present capacity expressed as a percentage of the battery's maximum rated capacity.*/
            }
            SETTLING_ERROR {
                doc /* difference between actual and commanded position at the end of a motion.*/
            }
            FOLLOWING_ERROR {
                doc /* difference between actual and commanded position at any specific point in time during a motion.*/
            }
            SETTLING_ERROR_LINEAR {
                doc /* difference between the commanded encoder/resolver position, and the actual encoder/resolver position when motion is complete.*/
            }
            SETTLING_ERROR_ANGULAR {
                doc /* angular difference between the commanded encoder/resolver position, and the actual encoder/resolver position when motion is complete.*/
            }
            FOLLOWING_ERROR_LINEAR {
                doc /* difference between the commanded encoder/resolver position and the actual encoder/resolver position at any specified point in time during a motion.*/
            }
            FOLLOWING_ERROR_ANGULAR {
                doc /* angular difference between the commanded encoder/resolver position and the actual encoder/resolver position at any specified point in time during a motion.*/
            }
            DISPLACEMENT_LINEAR {
                doc /* absolute value of the change in position along a vector.*/
            }
            DISPLACEMENT_ANGULAR {
                doc /* absolute value of the change in angular position around a vector*/
            }
            POSITION_CARTESIAN {
                doc /* point in a {{term(cartesian coordinate system)}}.*/
            }
            RESISTIVITY {
                doc /* inability of a material to conduct electricity.*/
            }
            FILL_HEIGHT {
                doc /* amount of a substance in a container.*/
            }
            PARTICLE_COUNT {
                doc /* number of particles counted by their size or other characteristics.*/
            }
            PARTICLE_SIZE {
                doc /* size of particles counted by their size or other characteristics.*/
            }
            WATER_HARDNESS {
                doc /* concentration of calcium carbonate (CaCO3) in water*/
            }
        }
        enum def EventEnum :> DataItemTypeEnum {
            doc /**/
            ACTIVE_AXES {
                doc /* set of axes currently associated with a {{block(Path)}} or {{block(Controller)}}.*/
            }
            ACTUATOR_STATE {
                doc /* operational state of an apparatus for moving or controlling a mechanism or system.*/
            }
            ALARM {
                doc /* **DEPRECATED:** Replaced with `CONDITION` category data items in Version 1.1.0.*/
            }
            ASSET_CHANGED {
                doc /* {{property(Asset::assetId)}} of the {{block(Asset)}} that has been changed.*/
            }
            ASSET_REMOVED {
                doc /* {{property(Asset::assetId)}} of the {{block(Asset)}} that has been removed.*/
            }
            AVAILABILITY {
                doc /* {{term(agent)}}'s ability to communicate with the data source.*/
            }
            AXIS_COUPLING {
                doc 
                /* describes the way the axes will be associated to each other. 
                 *   
                 * This is used in conjunction with `COUPLED_AXES` to indicate the way they are interacting.*/
            }
            AXIS_FEEDRATE_OVERRIDE {
                doc /* value of a signal or calculation issued to adjust the feedrate of an individual linear type axis.*/
            }
            AXIS_INTERLOCK {
                doc /* state of the axis lockout function when power has been removed and the axis is allowed to move freely.*/
            }
            AXIS_STATE {
                doc /* state of a {{block(Linear)}} or {{block(Rotary)}} component representing an axis.*/
            }
            BLOCK {
                doc /* line of code or command being executed by a {{block(Controller)}} entity.*/
            }
            BLOCK_COUNT {
                doc /* total count of the number of blocks of program code that have been executed since execution started.*/
            }
            CHUCK_INTERLOCK {
                doc /* state of an interlock function or control logic state intended to prevent the associated {{block(Chuck)}} component from being operated.*/
            }
            CHUCK_STATE {
                doc 
                /* operating state of a mechanism that holds a part or stock material during a manufacturing process. 
                 *
                 * It may also represent a mechanism that holds any other mechanism in place within a piece of equipment.*/
            }
            CODE {
                doc 
                /* programmatic code being executed.
                 *
                 * **DEPRECATED** in *Version 1.1*.*/
            }
            COMPOSITION_STATE {
                doc /* operating state of a mechanism represented by a {{block(Composition)}} entity.*/
            }
            CONTROLLER_MODE {
                doc /* current mode of the {{block(Controller)}} component.*/
            }
            CONTROLLER_MODE_OVERRIDE {
                doc /* setting or operator selection that changes the behavior of a piece of equipment.*/
            }
            COUPLED_AXES {
                doc /* set of associated axes.*/
            }
            DATE_CODE {
                doc /* time and date code associated with a material or other physical item.*/
            }
            DEVICE_UUID {
                doc /* identifier of another piece of equipment that is temporarily associated with a component of this piece of equipment to perform a particular function.*/
            }
            DIRECTION {
                doc /* direction of motion.*/
            }
            DOOR_STATE {
                doc /* operational state of a {{block(Door)}} component or composition element.*/
            }
            EMERGENCY_STOP {
                doc /* state of the emergency stop signal for a piece of equipment, controller path, or any other component or subsystem of a piece of equipment.*/
            }
            END_OF_BAR {
                doc /* indication of whether the end of a piece of bar stock being feed by a bar feeder has been reached.*/
            }
            EQUIPMENT_MODE {
                doc /* indication that a piece of equipment, or a sub-part of a piece of equipment, is performing specific types of activities.*/
            }
            EXECUTION {
                doc /* operating state of a {{block(Component)}}.*/
            }
            FUNCTIONAL_MODE {
                doc /* current intended production status of the {{block(Component)}}.*/
            }
            HARDNESS {
                doc /* hardness of a material.*/
            }
            LINE {
                doc 
                /* current line of code being executed.
                 *
                 * **DEPRECATED** in *Version 1.4.0*.*/
            }
            LINE_LABEL {
                doc /* identifier for a {{block(Block)}} of code in a {{block(Program)}}.*/
            }
            LINE_NUMBER {
                doc /* position of a block of program code within a control program.*/
            }
            MATERIAL {
                doc /* identifier of a material used or consumed in the manufacturing process*/
            }
            MATERIAL_LAYER {
                doc /* identifies the layers of material applied to a part or product as part of an additive manufacturing process.*/
            }
            MESSAGE {
                doc /* information to be transferred from a piece of equipment to a client software application.*/
            }
            OPERATOR_ID {
                doc /* identifier of the person currently responsible for operating the piece of equipment.*/
            }
            PALLET_ID {
                doc /* identifier for a pallet.*/
            }
            PART_COUNT {
                doc /* aggregate count of parts.*/
            }
            PART_DETECT {
                doc /* indication designating whether a part or work piece has been detected or is present.*/
            }
            PART_ID {
                doc /* identifier of a part in a manufacturing operation.*/
            }
            PART_NUMBER {
                doc 
                /* identifier of a part or product moving through the manufacturing process.
                 *
                 * **DEPRECATED** in *Version 1.7*. `PART_NUMBER` is now a `subType` of `PART_KIND_ID`.*/
            }
            PATH_FEEDRATE_OVERRIDE {
                doc /* value of a signal or calculation issued to adjust the feedrate for the axes associated with a {{block(Path)}} component that may represent a single axis or the coordinated movement of multiple axes.*/
            }
            PATH_MODE {
                doc /* describes the operational relationship between a {{block(Path)}} entity and another {{block(Path)}} entity for pieces of equipment comprised of multiple logical groupings of controlled axes or other logical operations.*/
            }
            POWER_STATE {
                doc /* indication of the status of the source of energy for an entity to allow it to perform its intended function or the state of an enabling signal providing permission for the entity to perform its functions.*/
            }
            POWER_STATUS {
                doc 
                /* status of the {{block(Component)}}.
                 *
                 * **DEPRECATED** in *Version 1.1.0*.*/
            }
            PROCESS_TIME {
                doc /* time and date associated with an activity or event.*/
            }
            PROGRAM {
                doc /* name of the logic or motion program being executed by the {{block(Controller)}} component.*/
            }
            PROGRAM_COMMENT {
                doc /* comment or non-executable statement in the control program.*/
            }
            PROGRAM_EDIT {
                doc 
                /* indication of the status of the {{block(Controller)}} components program editing mode.
                 *
                 * A program may be edited while another is executed.*/
            }
            PROGRAM_EDIT_NAME {
                doc 
                /* name of the program being edited. 
                 *
                 * This is used in conjunction with {{block(ProgramEdit)}} when in `ACTIVE` state. */
            }
            PROGRAM_HEADER {
                doc /* non-executable header section of the control program.*/
            }
            PROGRAM_LOCATION {
                doc /* {{term(URI)}} for the source file associated with {{block(Program)}}.*/
            }
            PROGRAM_LOCATION_TYPE {
                doc /* defines whether the logic or motion program defined by {{block(Program)}} is being executed from the local memory of the controller or from an outside source.*/
            }
            PROGRAM_NEST_LEVEL {
                doc /* indication of the nesting level within a control program that is associated with the code or instructions that is currently being executed.*/
            }
            ROTARY_MODE {
                doc /* current operating mode for a {{block(Rotary)}} type axis.*/
            }
            ROTARY_VELOCITY_OVERRIDE {
                doc /* percentage change to the velocity of the programmed velocity for a {{block(Rotary)}} axis.*/
            }
            SERIAL_NUMBER {
                doc /* serial number associated with a {{block(Component)}}, {{block(Asset)}}, or {{block(Device)}}.*/
            }
            SPINDLE_INTERLOCK {
                doc /* indication of the status of the spindle for a piece of equipment when power has been removed and it is free to rotate.*/
            }
            TOOL_ASSET_ID {
                doc /* identifier of an individual tool asset.*/
            }
            TOOL_GROUP {
                doc /* identifier for the tool group associated with a specific tool. Commonly used to designate spare tools.*/
            }
            TOOL_ID {
                doc 
                /* identifier of the tool currently in use for a given `Path`.
                 *
                 * **DEPRECATED** in *Version 1.2.0*.   See `TOOL_NUMBER`.*/
            }
            TOOL_NUMBER {
                doc /* identifier assigned by the {{block(Controller)}} component to a cutting tool when in use by a piece of equipment.*/
            }
            TOOL_OFFSET {
                doc /* reference to the tool offset variables applied to the active cutting tool.*/
            }
            USER {
                doc /* identifier of the person currently responsible for operating the piece of equipment.*/
            }
            VARIABLE {
                doc /* data whose meaning may change over time due to changes in the operation of a piece of equipment or the process being executed on that piece of equipment.*/
            }
            WAIT_STATE {
                doc /* indication of the reason that {{block(Execution)}} is reporting a value of `WAIT`.*/
            }
            WIRE {
                doc /* identifier for the type of wire used as the cutting mechanism in Electrical Discharge Machining or similar processes.*/
            }
            WORKHOLDING_ID {
                doc 
                /* identifier for the current workholding or part clamp in use by a piece of equipment.
                 *
                 * **DEPRECATION WARNING**: Recommend using `FIXTURE_ID` instead.*/
            }
            WORK_OFFSET {
                doc /* reference to offset variables for a work piece or part.*/
            }
            OPERATING_SYSTEM {
                doc /* Operating System (OS) of a {{block(Component)}}.*/
            }
            FIRMWARE {
                doc 
                /* embedded software of a {{block(Component)}}
                 * .*/
            }
            APPLICATION {
                doc /* application on a {{block(Component)}}.*/
            }
            LIBRARY {
                doc /* software library on a {{block(Component)}}*/
            }
            HARDWARE {
                doc /* hardware of a {{block(Component)}}.*/
            }
            NETWORK {
                doc /* network details of a {{block(Component)}}.*/
            }
            ROTATION {
                doc /* three space angular displacement of an object or coordinate system relative to a {{term(cartesian coordinate system)}}.*/
            }
            TRANSLATION {
                doc /* three space linear displacement of an object or coordinate system relative to a {{term(cartesian coordinate system)}}.*/
            }
            DEVICE_ADDED {
                doc /* {{term(UUID)}} of new device added to an {{term(MTConnect Agent)}}.*/
            }
            DEVICE_REMOVED {
                doc /* {{term(UUID)}} of a device removed from an {{term(MTConnect Agent)}}.*/
            }
            DEVICE_CHANGED {
                doc /* {{term(UUID)}} of the device whose {{term(metadata)}} has changed.*/
            }
            CONNECTION_STATUS {
                doc /* status of the connection between an {{term(adapter)}} and an {{term(agent)}}.*/
            }
            ADAPTER_SOFTWARE_VERSION {
                doc /* originator’s software version of the {{term(adapter)}}.*/
            }
            ADAPTER_URI {
                doc /* {{term(URI)}} of the {{term(adapter)}}.*/
            }
            MTCONNECT_VERSION {
                doc /* reference version of the MTConnect Standard supported by the {{term(adapter)}}.*/
            }
            SENSOR_ATTACHMENT {
                doc /* {{term(attachment)}} between a sensor and an entity.*/
            }
            PART_STATUS {
                doc /* state or condition of a part.*/
            }
            PROCESS_OCCURRENCE_ID {
                doc /* identifier of a process being executed by the device.*/
            }
            PROCESS_AGGREGATE_ID {
                doc /* identifier given to link the individual occurrence to a group of related occurrences, such as a process step in a process plan.*/
            }
            PROCESS_KIND_ID {
                doc /* identifier given to link the individual occurrence to a class of processes or process definition.*/
            }
            PART_GROUP_ID {
                doc /* identifier given to a collection of individual parts. */
            }
            PART_KIND_ID {
                doc /* identifier given to link the individual occurrence to a class of parts, typically distinguished by a particular part design.*/
            }
            PART_UNIQUE_ID {
                doc /* identifier given to a distinguishable, individual part. */
            }
            CONTROL_LIMIT {
                doc 
                /* set of limits used to indicate whether a process variable is stable and in control.
                 *
                 * **DEPRECATED** in *Version 2.5*. Replaced by `CONTROL_LIMITS`.*/
            }
            SPECIFICATION_LIMIT {
                doc 
                /* set of limits defining a range of values designating acceptable performance for a variable.
                 *
                 * **DEPRECATED** in *Version 2.5*. Replaced by  `SPECIFICATION_LIMITS`.*/
            }
            ALARM_LIMIT {
                doc 
                /* set of limits used to trigger warning or alarm indicators.
                 *
                 * **DEPRECATED** in *Version 2.5*. Replaced by  `ALARM_LIMITS`.*/
            }
            LOAD_COUNT {
                doc /* accumulation of the number of times an operation has attempted to, or is planned to attempt to, load materials, parts, or other items.*/
            }
            UNLOAD_COUNT {
                doc /* accumulation of the number of times an operation has attempted to, or is planned to attempt to, unload materials, parts, or other items.*/
            }
            TRANSFER_COUNT {
                doc /* accumulation of the number of times an operation has attempted to, or is planned to attempt to, transfer materials, parts, or other items from one location to another.*/
            }
            ACTIVATION_COUNT {
                doc /* accumulation of the number of times a function has attempted to, or is planned to attempt to, activate or be performed.*/
            }
            DEACTIVATION_COUNT {
                doc /* accumulation of the number of times a function has attempted to, or is planned to attempt to, deactivate or cease.*/
            }
            CYCLE_COUNT {
                doc /* accumulation of the number of times a cyclic function has attempted to, or is planned to attempt to execute.*/
            }
            VALVE_STATE {
                doc /* state of a valve is one of open, closed, or transitioning between the states.*/
            }
            LOCK_STATE {
                doc /* state or operating mode of a {{block(Lock)}}.*/
            }
            PROCESS_STATE {
                doc /* particular condition of the process occurrence at a specific time.*/
            }
            PART_PROCESSING_STATE {
                doc /* particular condition of the part occurrence at a specific time.*/
            }
            OPERATING_MODE {
                doc /* state of {{block(Component)}} or {{block(Composition)}} that describes the automatic or manual operation of the entity.*/
            }
            ASSET_COUNT {
                doc /* {{term(data set)}} of the number of {{termplural(Asset)}} of a given type for a {{term(Device)}}.*/
            }
            MAINTENANCE_LIST {
                doc /* actions or activities to be performed in support of a piece of equipment.*/
            }
            FIXTURE_ID {
                doc /* identifier for the current workholding or part clamp in use by a piece of equipment.*/
            }
            PART_COUNT_TYPE {
                doc /* interpretation of `PART_COUNT`.*/
            }
            CLOCK_TIME {
                doc /* time provided by a timing device at a specific point in time.*/
            }
            HOST_NAME {
                doc /* name of the host computer supplying data.*/
            }
            NETWORK_PORT {
                doc /* number of the TCP/IP or UDP/IP port for the connection endpoint.*/
            }
            LEAK_DETECT {
                doc /* indication designating whether a leak has been detected.*/
            }
            BATTERY_STATE {
                doc /* present status of the battery.*/
            }
            FEATURE_PERSISTENT_ID {
                doc /* {{term(UUID)}} of a {{term(feature)}}. {{cite(ISO 10303 AP 242/239)}}.*/
            }
            SENSOR_STATE {
                doc /* detection result of a sensor.*/
            }
            COMPONENT_DATA {
                doc /* {{block(Event)}} that represents a {{block(Component)}} where the {{block(EntryDefinition)}} identifies the {{block(Component)}} and the {{block(CellDefinition)}}s define the {{block(Component)}}'s observed {{block(DataItem)}}s.*/
            }
            WORK_OFFSETS {
                doc /* properties of each addressable work offset.*/
            }
            TOOL_OFFSETS {
                doc /* properties of each addressable tool offset.*/
            }
            FEATURE_MEASUREMENT {
                doc /* assessing elements of a {{term(feature)}}.*/
            }
            CHARACTERISTIC_PERSISTENT_ID {
                doc /* {{term(UUID)}} of the {{term(characteristic)}}.*/
            }
            MEASUREMENT_TYPE {
                doc /* class of measurement being performed. {{cite(QIF 3:2018 Section 6.3)}}*/
            }
            MEASUREMENT_VALUE {
                doc /* measurement based on the measurement type.*/
            }
            MEASUREMENT_UNITS {
                doc /* engineering units of the measurement.*/
            }
            CHARACTERISTIC_STATUS {
                doc /* pass/fail result of the measurement.*/
            }
            UNCERTAINTY_TYPE {
                doc /* method used to compute {{term(standard uncertainty)}}.*/
            }
            UNCERTAINTY {
                doc /* {{term(uncertainty)}} specified by {{block(UncertaintyType)}}.*/
            }
            SPECIFICATION_LIMITS {
                doc /* set of limits defining a range of values designating acceptable performance for a variable.*/
            }
            CONTROL_LIMITS {
                doc /* set of limits used to indicate whether a process variable is stable and in control.*/
            }
            ALARM_LIMITS {
                doc /* set of limits used to trigger warning or alarm indicators.*/
            }
            TOOL_CUTTING_ITEM {
                doc /* references the {{block(CuttingToolLifeCycle)}} {{block(CuttingItem)}} index related to the {{property(CuttingItem::indices)}} of the currently active cutting tool edge.*/
            }
            LOCATION_ADDRESS {
                doc /* structured information that allows the unambiguous determination of an object for purposes of identification and location. {{cite(ISO 19160-4:2017)}}*/
            }
            ACTIVE_POWER_SOURCE {
                doc /* active energy source for the {{block(Component)}}.*/
            }
            LOCATION_NARRATIVE {
                doc /* textual description of the location of an object or activity.*/
            }
            THICKNESS {
                doc /* dimension between two surfaces of an object, usually the dimension of smallest measure, for example an additive layer, or a depth of cut.*/
            }
            LOCATION_SPATIAL_GEOGRAPHIC {
                doc /* absolute geographic location defined by two coordinates, longitude and latitude and an elevation.*/
            }
            PART_INDEX {
                doc /* sequence of a part in a group of parts.*/
            }
            ASSOCIATED_ASSET_ID {
                doc /* {{property(Asset::assetId)}} of the {{block(Asset)}}s associated with a {{block(Component)}}.*/
            }
            ASSET_ADDED {
                doc /* {{property(Asset::assetId)}} of the {{block(Asset)}} that has been added.*/
            }
            TASK_ASSET_ID {
                doc /* {{property(Task::assetId)}} of the {{block(Task)}} that the {{block(Component)}} binds to*/
            }
            BINDING_STATE {
                doc /* state of the binding process when {{block(Component)}} participates in a task as a collaborator*/
            }
            SWING_ANGLE {
                doc /* angular range over which the object is designed to move about a fixed axis or pivot*/
            }
            SWING_RADIUS {
                doc /* maximal linear distance from the pivot or axis to the furthest point reached by the object’s swing*/
            }
            SWING_DIAMETER {
                doc /* maximal linear width (diameter) of the area described by the object’s movement about an axis*/
            }
            DEPTH {
                doc /* dimension or distance as measured downwards from the top*/
            }
            FIXTURE_ASSET_ID {
                doc /* {{property(Fixture::assetId)}} of the {{block(Fixture)}} that is associated with a {{block(Component)}}*/
            }
        }
        enum def ConditionEnum :> SampleEnum, EventEnum {
            COMMUNICATIONS {
                doc /* indication that the piece of equipment has experienced a communications failure.*/
            }
            DATA_RANGE {
                doc /* indication that the value of the data associated with a measured value or a calculation is outside of an expected range.*/
            }
            LOGIC_PROGRAM {
                doc /* indication that an error occurred in the logic program or programmable logic controller (PLC) associated with a piece of equipment.*/
            }
            MOTION_PROGRAM {
                doc /* indication that an error occurred in the motion program associated with a piece of equipment.*/
            }
            SYSTEM {
                doc /* general purpose indication associated with an electronic component of a piece of equipment or a controller that represents a fault that is not associated with the operator, program, or hardware.*/
            }
            ACTUATOR {
                doc /* indication of a fault associated with an actuator.*/
            }
        }
        enum def MotionActuationTypeEnum {
            DIRECT {
                doc /* movement is initiated by the component.*/
            }
            VIRTUAL {
                doc /* motion is computed and is used for expressing an imaginary movement.*/
            }
            NONE {
                doc 
                /* no actuation of this axis.
                 *
                 * > Note: Actuation of `NONE` can be either a derived `REVOLUTE` or `PRISMATIC` motion or static `FIXED` relationship.*/
            }
        }
        enum def MotionTypeEnum {
            PRISMATIC {
                doc /* sliding linear motion along an axis with a fixed range of motion.*/
            }
            CONTINUOUS {
                doc /* revolves around an axis with a continuous range of motion.*/
            }
            REVOLUTE {
                doc /* rotates around an axis with a fixed range of motion.*/
            }
            FIXED {
                doc /* axis does not move.*/
            }
        }
        enum def CoordinateSystemTypeEnum {
            WORLD {
                doc 
                /* stationary coordinate system referenced to earth, which is independent of the robot motion. {{cite(ISO 9787:2013)}}
                 *
                 * For non-robotic devices, stationary coordinate system referenced to earth, which is independent of the motion of a piece of equipment.*/
            }
            BASE {
                doc 
                /* coordinate system referenced to the base mounting surface. {{cite(ISO 9787:2013)}}
                 *
                 * A base mounting surface is a connection surface between the arm and its supporting structure.{{cite(ISO 9787:2013)}}
                 *
                 * For non-robotic devices, it is the connection surface between the device and its supporting structure.*/
            }
            OBJECT {
                doc /* coordinate system referenced to the object. {{cite(ISO 9787:2013)}}*/
            }
            TASK {
                doc /* coordinate system referenced to the site of the task. {{cite(ISO 9787:2013)}}*/
            }
            MECHANICAL_INTERFACE {
                doc /* coordinate system referenced to the mechanical interface. {{cite(ISO 9787:2013)}}*/
            }
            TOOL {
                doc /* coordinate system referenced to the tool or to the end effector attached to the mechanical interface. {{cite(ISO 9787:2013)}}*/
            }
            MOBILE_PLATFORM {
                doc /* coordinate system referenced to one of the components of a mobile platform. {{cite(ISO 8373:2012)}}*/
            }
            MACHINE {
                doc /* coordinate system referenced to the home position and orientation of the primary axes of a piece of equipment.*/
            }
            CAMERA {
                doc /* coordinate system referenced to the sensor which monitors the site of the task. {{cite(ISO 9787:2013)}}*/
            }
        }
        enum def DataItemRelationshipTypeEnum {
            ATTACHMENT {
                doc /* reference to a {{block(DataItem)}} that associates the values with an external entity.*/
            }
            COORDINATE_SYSTEM {
                doc /* referenced {{block(DataItem)}} provides the `id` of the effective Coordinate System.*/
            }
            LIMIT {
                doc /* referenced {{block(DataItem)}} provides process limits.*/
            }
            OBSERVATION {
                doc /* referenced {{block(DataItem)}} provides the observed values.*/
            }
        }
        enum def SpecificationRelationshipTypeEnum {
            LIMIT {
                doc /* referenced {{block(Specification)}} provides process limits.*/
            }
        }
        enum def MediaTypeEnum {
            STEP {
                doc /* ISO 10303 STEP AP203 or AP242 format.*/
            }
            STL {
                doc /* STereoLithography file format.*/
            }
            GDML {
                doc /* Geometry Description Markup Language.*/
            }
            OBJ {
                doc /* Wavefront OBJ file format.*/
            }
            COLLADA {
                doc /* ISO 17506.*/
            }
            IGES {
                doc /* Initial Graphics Exchange Specification.*/
            }
            '3DS' {
                doc /* Autodesk file format.*/
            }
            ACIS {
                doc /* Dassault file format.*/
            }
            X_T {
                doc /* Parasolid XT Siemens data interchange format.*/
            }
            QIF_MBD {
                doc /* provides the 3D geometric boundary representation used to associate with product information.*/
            }
        }
        enum def OriginatorEnum {
            MANUFACTURER {
                doc /* manufacturer of a piece of equipment or {{block(Component)}}.*/
            }
            USER {
                doc /* owner or implementer of a piece of equipment or {{block(Component)}}.*/
            }
        }
        enum def QIFDocumentTypeEnum {
            MEASUREMENT_RESOURCE;
            PLAN;
            PRODUCT;
            RESULTS;
            RULES;
            STATISTICS;
        }
        enum def ProcessStateEnum {
            INITIALIZING {
                doc /* device is preparing to execute the process occurrence.*/
            }
            READY {
                doc /* process occurrence is ready to be executed.*/
            }
            ACTIVE {
                doc /* process occurrence is actively executing.*/
            }
            COMPLETE {
                doc /* process occurrence is now finished.*/
            }
            INTERRUPTED {
                doc /* process occurrence has been stopped and may be resumed.*/
            }
            ABORTED {
                doc /* process occurrence has come to a premature end and cannot be resumed.*/
            }
        }
        enum def AssetTypeEnum {
            CuttingTool {
                doc /* {{block(CuttingTool)}} {{block(Asset)}} type.*/
            }
            File {
                doc /* {{block(File)}} {{block(Asset)}} type. */
            }
            QIFDocumentWrapper {
                doc /* {{block(QIFDocumentWrapper)}} {{block(Asset)}} type. */
            }
            RawMaterial {
                doc /* {{block(RawMaterial)}} {{block(Asset)}} type. */
            }
            CuttingToolArchetype;
            FileArchetype;
        }
        enum def ChuckStateEnum {
            OPEN {
                doc /* {{block(Chuck)}} is open to the point of a positive confirmation.*/
            }
            CLOSED {
                doc /* {{block(Chuck)}} is closed to the point of a positive confirmation.*/
            }
            UNLATCHED {
                doc 
                /* {{block(Chuck)}} is not closed to the point of a positive confirmation and not open to the point of a positive confirmation. 
                 *
                 * It is in an intermediate position.*/
            }
        }
        enum def AxisCouplingEnum {
            TANDEM {
                doc /* axes are physically connected to each other and operate as a single unit.*/
            }
            SYNCHRONOUS {
                doc /* axes are not physically connected to each other but are operating together in lockstep.*/
            }
            MASTER {
                doc /* axis is the master of the {{block(CoupledAxes)}}.*/
            }
            SLAVE {
                doc /* axis is a slave to the {{block(CoupledAxes)}}.*/
            }
        }
        enum def PartStatusEnum {
            PASS {
                doc /* part conforms to given requirements.*/
            }
            FAIL {
                doc /* part does not conform to some given requirements.*/
            }
        }
        enum def DirectionRotaryEnum {
            CLOCKWISE {
                doc /* clockwise rotation using the right-hand rule.*/
            }
            COUNTER_CLOCKWISE {
                doc /* counter-clockwise rotation using the right-hand rule.*/
            }
            NONE {
                doc /* no direction.*/
            }
        }
        enum def FileStateEnum {
            EXPERIMENTAL {
                doc /* used for processes other than production or otherwise defined.*/
            }
            PRODUCTION {
                doc /* used for production processes.*/
            }
            REVISION {
                doc /* content is modified from `PRODUCTION` or `EXPERIMENTAL`.*/
            }
        }
        enum def CriticalityTypeEnum {
            CRITICAL {
                doc /* services or functions provided by the associated element is required for the operation of this element.*/
            }
            NONCRITICAL {
                doc /* services or functions provided by the associated element is not required for the operation of this element.*/
            }
        }
        enum def CompositionStateMotionEnum {
            OPEN {
                doc /* position of the {{block(Composition)}} is open to the point of a positive confirmation.*/
            }
            UNLATCHED {
                doc 
                /* position of the {{block(Composition)}} is not open to the
                 * point of a positive confirmation and is not closed to the point of a positive confirmation. 
                 *
                 * It is in an intermediate position.*/
            }
            CLOSED {
                doc /* position of the {{block(Composition)}} is closed to the point of a positive confirmation.*/
            }
        }
        enum def ActuatorStateEnum {
            ACTIVE {
                doc /* {{block(Actuator)}} is operating.*/
            }
            INACTIVE {
                doc /* {{block(Actuator)}} is not operating.*/
            }
        }
        enum def ConnectionStatusEnum {
            CLOSED {
                doc /* no connection at all.*/
            }
            LISTEN {
                doc /* {{term(agent)}} is waiting for a connection request from an {{term(adapter)}}.*/
            }
            ESTABLISHED {
                doc 
                /* open connection.
                 *
                 * The normal state for the data transfer phase of the connection.*/
            }
        }
        enum def RoleTypeEnum {
            SYSTEM {
                doc /* associated element performs the functions of a {{block(System)}} for this element.*/
            }
            AUXILIARY {
                doc /* associated element performs the functions as an `Auxiliary` for this element.*/
            }
        }
        enum def PathModeEnum {
            INDEPENDENT {
                doc /* path is operating independently and without the influence of another path.*/
            }
            MASTER {
                doc /* path provides information or state values that influences the operation of other {{block(DataItem)}} of similar type.*/
            }
            SYNCHRONOUS {
                doc /* physical or logical parts which are not physically connected to each other but are operating together.*/
            }
            MIRROR {
                doc /* axes associated with the path are mirroring the motion of the `MASTER` path.*/
            }
        }
        enum def CompositionStateActionEnum {
            ACTIVE {
                doc /* {{block(Composition)}} is operating.*/
            }
            INACTIVE {
                doc /* {{block(Composition)}} is not operating.*/
            }
        }
        private attribute def MILLIMETER :> unit {
            doc /* float that represents measurement in millimeter.*/
        }
        enum def PartProcessingStateEnum {
            NEEDS_PROCESSING {
                doc 
                /* part occurrence is not actively being processed, but the processing has not ended. 
                 *
                 * Processing requirements exist that have not yet been fulfilled. This is the default entry state when the part occurrence is originally received. In some cases, the part occurrence may return to this state while it waits for additional processing to be performed.*/
            }
            IN_PROCESS {
                doc /* part occurrence is actively being processed.*/
            }
            PROCESSING_ENDED {
                doc 
                /* part occurrence is no longer being processed. 
                 *
                 * A general state when the reason for termination is unknown.*/
            }
            PROCESSING_ENDED_COMPLETE {
                doc /* part occurrence has completed processing successfully.*/
            }
            PROCESSING_ENDED_STOPPED {
                doc 
                /* process has been stopped during the processing. 
                 *
                 * The part occurrence will require special treatment.*/
            }
            PROCESSING_ENDED_ABORTED {
                doc /* processing of the part occurrence has come to a premature end.*/
            }
            PROCESSING_ENDED_LOST {
                doc /* terminal state when the part occurrence has been removed from the equipment by an external entity and it no longer exists at the equipment.*/
            }
            PROCESSING_ENDED_SKIPPED {
                doc /* part occurrence has been skipped for processing on the piece of equipment.*/
            }
            PROCESSING_ENDED_REJECTED {
                doc /* part occurrence has been processed completely. However, the processing may have a problem.*/
            }
            WAITING_FOR_TRANSIT {
                doc /* part occurrence is waiting for transit.*/
            }
            IN_TRANSIT {
                doc /* part occurrence is being transported to its destination.*/
            }
            TRANSIT_COMPLETE {
                doc /* part occurrence has been placed at its designated destination.*/
            }
        }
        enum def ControllerModeEnum {
            AUTOMATIC {
                doc /* {{block(Controller)}} is configured to automatically execute a program.*/
            }
            MANUAL {
                doc 
                /* {{block(Controller)}} is not executing an active program. 
                 *
                 * It is capable of receiving instructions from an external source – typically an operator. The {{block(Controller)}} executes operations based on the instructions received from the external source.*/
            }
            MANUAL_DATA_INPUT {
                doc 
                /* operator can enter a series of operations for the {{block(Controller)}} to perform.
                 *
                 * The {{block(Controller)}} will execute this specific series of operations and then stop.*/
            }
            SEMI_AUTOMATIC {
                doc /* {{block(Controller)}} is operating in a mode that restricts the active program from processing its next process step without operator intervention.*/
            }
            EDIT {
                doc /* {{block(Controller)}} is currently functioning as a programming device and is not capable of executing an active program.*/
            }
            FEED_HOLD {
                doc /* axes of the device are commanded to stop, but the spindle continues to function.*/
            }
        }
        enum def DirectionLinearEnum {
            POSITIVE {
                doc /* linear position is increasing.*/
            }
            NEGATIVE {
                doc /* linear position is decreasing.*/
            }
            NONE {
                doc /* no direction.*/
            }
        }
        enum def EndOfBarEnum {
            YES {
                doc /* {{block(EndOfBar)}} has been reached.*/
            }
            NO {
                doc /* {{block(EndOfBar)}} has not been reached.*/
            }
        }
        enum def LocationTypeEnum {
            doc /* Enumeration for Location types*/
            POT {
                doc /* number of the pot in the tool handling system.*/
            }
            STATION {
                doc /* tool location in a horizontal turning machine.*/
            }
            CRIB {
                doc /* location with regard to a tool crib.*/
            }
            SPINDLE {
                doc /* location associated with a {{term(spindle)}}.*/
            }
            TRANSFER_POT {
                doc /* location for a tool awaiting transfer from a tool magazine to spindle or a turret.*/
            }
            RETURN_POT {
                doc /* location for a tool removed from a {{term(spindle)}} or turret and awaiting return to a tool magazine.*/
            }
            STAGING_POT {
                doc /* location for a tool awaiting transfer to a tool magazine or turret from outside of the piece of equipment.*/
            }
            REMOVAL_POT {
                doc /* location for a tool removed from a tool magazine or turret awaiting transfer to a location outside of the piece of equipment.*/
            }
            EXPIRED_POT {
                doc /* location for a tool that is no longer usable and is awaiting removal from a tool magazine or turret.*/
            }
            END_EFFECTOR {
                doc /* location associated with an end effector.*/
            }
        }
        enum def ValveStateEnum {
            OPEN {
                doc 
                /* {{block(ValveState)}} where flow is allowed and the aperture is static.
                 *
                 * > Note: For a binary value, `OPEN` indicates the valve has the maximum possible aperture.*/
            }
            OPENING {
                doc /* valve is transitioning from a `CLOSED` state to an `OPEN` state.*/
            }
            CLOSED {
                doc /* {{block(ValveState)}} where flow is not possible, the aperture is static, and the valve is completely shut.*/
            }
            CLOSING {
                doc /* valve is transitioning from an `OPEN` state to a `CLOSED` state.*/
            }
        }
        enum def CodeEnum {
            BDX {
                doc /* largest diameter of the body of a tool item.*/
            }
            LBX {
                doc /* distance measured along the X axis from that point of the item closest to the workpiece, including the cutting item for a tool item but excluding a protruding locking mechanism for an adaptive item, to either the front of the flange on a flanged body or the beginning of the connection interface feature on the machine side for cylindrical or prismatic shanks.*/
            }
            APMX {
                doc /* maximum engagement of the cutting edge or edges with the workpiece measured perpendicular to the feed motion.*/
            }
            DC {
                doc /* maximum diameter of a circle on which the defined point Pk of each of the master inserts is located on a tool item. The normal of the machined peripheral surface points towards the axis of the cutting tool.*/
            }
            DF {
                doc /* dimension between two parallel tangents on the outside edge of a flange.*/
            }
            OAL {
                doc /* largest length dimension of the cutting tool including the master insert where applicable.*/
            }
            DMM {
                doc /* dimension of the diameter of a cylindrical portion of a tool item or an adaptive item that can participate in a connection.*/
            }
            H {
                doc /* dimension of the height of the shank.*/
            }
            LS {
                doc /* dimension of the length of the shank.*/
            }
            LUX {
                doc /* maximum length of a cutting tool that can be used in a particular cutting operation including the non-cutting portions of the tool.*/
            }
            LPR {
                doc /* dimension from the yz-plane to the furthest point of the tool item or adaptive item measured in the -X direction.*/
            }
            WT {
                doc 
                /* total weight of the cutting tool in grams. 
                 *
                 * The force exerted by the mass of the cutting tool.*/
            }
            LF {
                doc 
                /* distance from the gauge plane or from the end of the shank to the furthest point on the tool, if a gauge plane does not exist, to the cutting reference point determined by the main function of the tool. 
                 *
                 * The {{block(CuttingTool)}} functional length will be the length of the entire tool, not a single cutting item. Each {{block(CuttingItem)}} can have an independent {{block(FunctionalLength)}} represented in its measurements. */
            }
            CRP {
                doc /* theoretical sharp point of the cutting tool from which the major functional dimensions are taken.*/
            }
            L {
                doc /* theoretical length of the cutting edge of a cutting item over sharp corners.*/
            }
            DRVA {
                doc /* angle between the driving mechanism locator on a tool item and the main cutting edge.*/
            }
            WF {
                doc /* distance between the cutting reference point and the rear backing surface of a turning tool or the axis of a boring bar.*/
            }
            IC {
                doc /* diameter of a circle to which all edges of a equilateral and round regular insert are tangential.*/
            }
            SIG {
                doc /* angle between the major cutting edge and the same cutting edge rotated by 180 degrees about the tool axis.*/
            }
            KAPR {
                doc /* angle between the tool cutting edge plane and the tool feed plane measured in a plane parallel the xy-plane.*/
            }
            PSIR {
                doc /* angle between the tool cutting edge plane and a plane perpendicular to the tool feed plane measured in a plane parallel the xy-plane.*/
            }
            'N/A' {
                doc 
                /* angle of the tool with respect to the workpiece for a given process. 
                 *
                 * The value is application specific.*/
            }
            BS {
                doc /* measure of the length of a wiper edge of a cutting item.*/
            }
            SDLx {
                doc /* length of a portion of a stepped tool that is related to a corresponding cutting diameter measured from the cutting reference point of that cutting diameter to the point on the next cutting edge at which the diameter starts to change.*/
            }
            STAx {
                doc /* angle between a major edge on a step of a stepped tool and the same cutting edge rotated 180 degrees about its tool axis.*/
            }
            DCx {
                doc 
                /* diameter of a circle on which the defined point Pk located on this cutting tool.
                 *
                 * The normal of the machined peripheral surface points towards the axis of the cutting tool.*/
            }
            HF {
                doc /* distance from the basal plane of the tool item to the cutting point.*/
            }
            RE {
                doc /* nominal radius of a rounded corner measured in the X Y-plane.*/
            }
            LFx {
                doc 
                /* distance from the gauge plane or from the end of the shank of the cutting tool, if a gauge plane does not exist, to the cutting reference point determined by the main function of the tool. 
                 *
                 * This measurement will be with reference to the cutting tool and **MUST NOT** exist without a cutting tool.*/
            }
            BCH {
                doc /* flat length of a chamfer.*/
            }
            CHW {
                doc /* width of the chamfer.*/
            }
            W1 {
                doc /* insert width when an inscribed circle diameter is not practical.*/
            }
        }
        enum def ApplicationCategoryEnum {
            ASSEMBLY {
                doc /* files regarding the fully assembled product.*/
            }
            DEVICE {
                doc /* device related files.*/
            }
            HANDLING {
                doc /* files relating to the handling of material.*/
            }
            MAINTENANCE {
                doc /* files relating to equipment maintenance.*/
            }
            PART {
                doc /* files relating to a part.*/
            }
            PROCESS {
                doc /* files related to the manufacturing process.*/
            }
            INSPECTION {
                doc /* files related to the quality inspection.*/
            }
            SETUP {
                doc /* files related to the setup of a process.*/
            }
        }
        enum def CutterStatusTypeEnum {
            doc /* Enumeration for CutterStatus values.*/
            NEW {
                doc 
                /* new tool that has not been used or first use. 
                 *
                 * Marks the start of the tool history.*/
            }
            AVAILABLE {
                doc 
                /* tool is available for use. 
                 *
                 * If this is not present, the tool is currently not ready to be used.*/
            }
            UNAVAILABLE {
                doc /* tool is unavailable for use in metal removal. */
            }
            ALLOCATED {
                doc /* tool is has been committed to a piece of equipment for use and is not available for use in any other piece of equipment.*/
            }
            UNALLOCATED {
                doc /* tool has not been committed to a process and can be allocated.*/
            }
            MEASURED {
                doc /* tool has been measured.*/
            }
            RECONDITIONED {
                doc /* tool has been reconditioned.*/
            }
            USED {
                doc /* tool is in process and has remaining tool life.*/
            }
            EXPIRED {
                doc /* tool has reached the end of its useful life.*/
            }
            BROKEN {
                doc /* premature tool failure.*/
            }
            NOT_REGISTERED {
                doc /* tool cannot be used until it is entered into the system.*/
            }
            UNKNOWN {
                doc /* tool is an indeterminate state. This is the default value.*/
            }
        }
        enum def CompositionStateLateralEnum {
            RIGHT {
                doc /* position of the {{block(Composition)}} is oriented to the right to the point of a positive confirmation.*/
            }
            LEFT {
                doc /* position of the {{block(Composition)}} is oriented to the left to the point of a positive confirmation.*/
            }
            TRANSITIONING {
                doc 
                /* position of the {{block(Composition)}} is not oriented to the right to the point of a positive confirmation and is not oriented to the left to the point of a positive confirmation. 
                 *
                 * It is in an intermediate position.*/
            }
        }
        enum def PartDetectEnum {
            PRESENT {
                doc /* part or work piece is detected or is present.*/
            }
            NOT_PRESENT {
                doc /* part or work piece is not detected or is not present.*/
            }
        }
        enum def ExecutionEnum {
            READY {
                doc 
                /* {{block(Component)}} is ready to execute instructions.
                 *
                 * It is currently idle.*/
            }
            ACTIVE {
                doc /* {{block(Component)}} is actively executing an instruction.*/
            }
            INTERRUPTED {
                doc 
                /* {{block(Component)}} suspends the execution of the program due to an external signal.
                 *
                 * Action is required to resume execution.*/
            }
            FEED_HOLD {
                doc /* motion of the active axes are commanded to stop at their current position.*/
            }
            STOPPED {
                doc /* {{block(Component)}} program is not `READY` to execute.*/
            }
            OPTIONAL_STOP {
                doc 
                /* command from the program has intentionally interrupted execution.
                 *
                 * The {{block(Component)}} **MAY** have another state that indicates if the execution is interrupted or the execution ignores the interrupt instruction.*/
            }
            PROGRAM_STOPPED {
                doc 
                /* command from the program has intentionally interrupted execution.
                 *
                 * Action is required to resume execution.*/
            }
            PROGRAM_COMPLETED {
                doc /* program completed execution.*/
            }
            WAIT {
                doc 
                /* {{block(Component)}} suspends execution while a secondary operation executes.
                 *
                 * Execution resumes automatically once the secondary operation completes.*/
            }
            PROGRAM_OPTIONAL_STOP {
                doc 
                /* program has been intentionally optionally stopped using an M01 or similar code.
                 *
                 * **DEPRECATED** in *version 1.4* and replaced with `OPTIONAL_STOP`.*/
            }
        }
        private attribute def DEGREE :> unit {
            doc /* float that represents angle in degrees.*/
        }
        enum def AvailabilityEnum {
            AVAILABLE {
                doc /* data source is active and capable of providing data.*/
            }
            UNAVAILABLE {
                doc /* data source is either inactive or not capable of providing data.*/
            }
        }
        enum def ProgramEditEnum {
            ACTIVE {
                doc /* {{block(Controller)}} is in the program edit mode.*/
            }
            READY {
                doc /* {{block(Controller)}} is capable of entering the program edit mode and no function is inhibiting a change to that mode.*/
            }
            NOT_READY {
                doc /* {{block(Controller)}} is being inhibited by a function from entering the program edit mode.*/
            }
        }
        enum def ControllerModeOverrideEnum {
            ON {
                doc /* {{block(ControllerModeOverride)}} is in the `ON` state and the mode override is active.*/
            }
            OFF {
                doc /* {{block(ControllerModeOverride)}} is in the `OFF` state and the mode override is inactive.*/
            }
        }
        enum def FunctionalModeEnum {
            PRODUCTION {
                doc /* {{block(Component)}} is currently producing product, ready to produce product, or its current intended use is to be producing product.*/
            }
            SETUP {
                doc 
                /* {{block(Component)}} is not currently producing product. 
                 *
                 * It is being prepared or modified to begin production of product.*/
            }
            TEARDOWN {
                doc 
                /* {{block(Component)}} is not currently producing product.
                 *
                 * Typically, it has completed the production of a product and is being modified or returned to a neutral state such that it may then be prepared to begin production of a different product.*/
            }
            MAINTENANCE {
                doc 
                /* {{block(Component)}} is not currently producing product.
                 *
                 * It is currently being repaired, waiting to be repaired, or has not yet been returned to a normal production status after maintenance has been performed.*/
            }
            PROCESS_DEVELOPMENT {
                doc /* {{block(Component)}} is being used to prove-out a new process, testing of equipment or processes, or any other active use that does not result in the production of product.*/
            }
        }
        enum def WaitStateEnum {
            POWERING_UP {
                doc /* execution is waiting while the equipment is powering up and is not currently available to begin producing parts or products.*/
            }
            POWERING_DOWN {
                doc /* execution is waiting while the equipment is powering down but has not fully reached a stopped state.*/
            }
            PART_LOAD {
                doc /* execution is waiting while one or more discrete workpieces are being loaded.*/
            }
            PART_UNLOAD {
                doc /* execution is waiting while one or more discrete workpieces are being unloaded.*/
            }
            TOOL_LOAD {
                doc /* execution is waiting while a tool or tooling is being loaded.*/
            }
            TOOL_UNLOAD {
                doc /* execution is waiting while a tool or tooling is being unloaded.*/
            }
            MATERIAL_LOAD {
                doc /* execution is waiting while material is being loaded.*/
            }
            MATERIAL_UNLOAD {
                doc /* execution is waiting while material is being unloaded.*/
            }
            SECONDARY_PROCESS {
                doc /* execution is waiting while another process is completed before the execution can resume.*/
            }
            PAUSING {
                doc /* execution is waiting while the equipment is pausing but the piece of equipment has not yet reached a fully paused state.*/
            }
            RESUMING {
                doc /* execution is waiting while the equipment is resuming the production cycle but has not yet resumed execution.*/
            }
        }
        enum def RotaryModeEnum {
            SPINDLE {
                doc /* axis is functioning as a spindle.*/
            }
            INDEX {
                doc /* axis is configured to index.*/
            }
            CONTOUR {
                doc /* position of the axis is being interpolated.*/
            }
        }
        enum def CompositionStateSwitchedEnum {
            ON {
                doc /* activation state of the {{block(Composition)}} is in an `ON` condition, it is operating, or it is powered.*/
            }
            OFF {
                doc /* activation state of the {{block(Composition)}} is in an `OFF` condition, it is not operating, or it is not powered.*/
            }
        }
        enum def EmergencyStopEnum {
            ARMED {
                doc /* emergency stop circuit is complete and the piece of equipment, component, or composition is allowed to operate. */
            }
            TRIGGERED {
                doc /* operation of the piece of equipment, component, or composition is inhibited.*/
            }
        }
        enum def LockStateEnum {
            LOCKED {
                doc /* mechanism is engaged and preventing the associated {{block(Component)}} from being opened or operated.*/
            }
            UNLOCKED {
                doc /* mechanism is disengaged and the associated {{block(Component)}} is able to be opened or operated.*/
            }
        }
        enum def AxisStateEnum {
            HOME {
                doc /* axis is in its home position.*/
            }
            TRAVEL {
                doc /* axis is in motion.*/
            }
            PARKED {
                doc 
                /* axis has been moved to a fixed position and is being maintained in that position either electrically or mechanically. 
                 *
                 * Action is required to release the axis from this position.*/
            }
            STOPPED {
                doc /* axis is stopped.*/
            }
        }
        enum def InterfaceStateEnum {
            ENABLED {
                doc /* {{block(Interface)}} is currently operational and performing as expected.*/
            }
            DISABLED {
                doc /* {{block(Interface)}} is currently not operational.*/
            }
        }
        enum def RelationshipTypeEnum {
            PARENT {
                doc /* functions as a parent in the relationship with the associated element.*/
            }
            CHILD {
                doc /* functions as a child in the relationship with the associated element.*/
            }
            PEER {
                doc /* functions as a peer which provides equal functionality and capabilities in the relationship with the associated element.*/
            }
        }
        enum def FormatTypeEnum {
            doc /* Enumeration for CuttingToolDefinition format values.*/
            EXPRESS {
                doc /* document will confirm to the ISO 10303 Part 21 standard.*/
            }
            TEXT {
                doc /* document will be a text representation of the tool data.*/
            }
            UNDEFINED {
                doc /* document will be provided in an undefined format.*/
            }
            XML {
                doc /* default value for the definition. The content will be an {{term(XML)}} document.*/
            }
        }
        enum def CompositionTypeEnum {
            ACTUATOR {
                doc 
                /* {{block(Composition)}} composed of a mechanism that moves or controls a mechanical part of a piece of equipment.
                 *
                 * It takes energy usually provided by air, electric current, or liquid and converts the energy into some kind of motion. */
            }
            AMPLIFIER {
                doc /* {{block(Composition)}} composed of an electronic component or circuit that amplifies power, electric current, or voltage.*/
            }
            BALLSCREW {
                doc /* {{block(Composition)}} composed of a mechanical structure that transforms rotary motion into linear motion.*/
            }
            BELT {
                doc /* {{block(Composition)}} composed of an endless flexible band that transmits motion for a piece of equipment or conveys materials and objects.*/
            }
            BRAKE {
                doc /* {{block(Composition)}} composed of a mechanism that slows down or stops a moving object by the absorption or transfer of the energy of momentum, usually by means of friction, electrical force, or magnetic force.*/
            }
            CHAIN {
                doc /* {{block(Composition)}} composed of an interconnected series of objects that band together and transmit motion for a piece of equipment or to convey materials and objects.*/
            }
            CHOPPER {
                doc /* {{block(Composition)}} composed of a mechanism that breaks material into smaller pieces.*/
            }
            CHUCK {
                doc /* {{block(Composition)}} composed of a mechanism that holds a part, stock material, or any other item in place.*/
            }
            CHUTE {
                doc /* {{block(Composition)}} composed of an inclined channel that conveys material.*/
            }
            CIRCUIT_BREAKER {
                doc /* {{block(Composition)}} composed of a mechanism that interrupts an electric circuit.*/
            }
            CLAMP {
                doc /* {{block(Composition)}} composed of a mechanism that strengthens, supports, or fastens objects in place.*/
            }
            COMPRESSOR {
                doc /* {{block(Composition)}} composed of a pump or other mechanism that reduces volume and increases pressure of gases in order to condense the gases to drive pneumatically powered pieces of equipment.*/
            }
            DOOR {
                doc /* {{block(Composition)}} composed of a mechanical mechanism or closure that covers a physical access portal into a piece of equipment allowing or restricting access to other parts of the equipment.*/
            }
            DRAIN {
                doc /* {{block(Composition)}} composed of a mechanism that allows material to flow for the purpose of drainage from, for example, a vessel or tank.*/
            }
            ENCODER {
                doc /* {{block(Composition)}} composed of a mechanism that measures rotary position.*/
            }
            EXPOSURE_UNIT {
                doc /* {{block(Composition)}} composed of a mechanism that emits a type of radiation.*/
            }
            EXTRUSION_UNIT {
                doc /* {{block(Composition)}} composed of a mechanism that dispenses liquid or powered materials.*/
            }
            FAN {
                doc /* {{block(Composition)}} composed of a mechanism that produces a current of air.*/
            }
            FILTER {
                doc /* {{block(Composition)}} composed of a substance or structure that allows liquids or gases to pass through to remove suspended impurities or to recover solids.*/
            }
            GALVANOMOTOR {
                doc /* {{block(Composition)}} composed of an electromechanical actuator that produces deflection of a beam of light or energy in response to electric current through its coil in a magnetic field.*/
            }
            GRIPPER {
                doc /* {{block(Composition)}} composed of a mechanism that holds a part, stock material, or any other item in place.*/
            }
            HOPPER {
                doc /* {{block(Composition)}} composed of a chamber or bin that stores materials temporarily, typically being filled through the top and dispensed through the bottom.*/
            }
            LINEAR_POSITION_FEEDBACK {
                doc /* {{block(Composition)}} composed of a mechanism that measures linear motion or position.*/
            }
            MOTOR {
                doc /* {{block(Composition)}} composed of a mechanism that converts electrical, pneumatic, or hydraulic energy into mechanical energy.*/
            }
            OIL {
                doc /* {{block(Composition)}} composed of a viscous liquid.*/
            }
            POWER_SUPPLY {
                doc /* {{block(Composition)}} composed of a unit that provides power to electric mechanisms.*/
            }
            PULLEY {
                doc /* {{block(Composition)}} composed of a mechanism or wheel that turns in a frame or block and serves to change the direction of or to transmit force.*/
            }
            PUMP {
                doc /* {{block(Composition)}} composed of an apparatus that raises, drives, exhausts, or compresses fluids or gases by means of a piston, plunger, or set of rotating vanes.*/
            }
            REEL {
                doc /* {{block(Composition)}} composed of a rotary storage unit for material.*/
            }
            SENSING_ELEMENT {
                doc /* {{block(Composition)}} composed of a mechanism that provides a signal or measured value.*/
            }
            SPREADER {
                doc /* {{block(Composition)}} composed of a mechanism that flattens or spreads materials.*/
            }
            STORAGE_BATTERY {
                doc /* {{block(Composition)}} composed of one or more cells that converts chemical energy to electricity and serves as a source of power. */
            }
            SWITCH {
                doc /* {{block(Composition)}} composed of a mechanism that turns on or off an electric current or makes or breaks a circuit.*/
            }
            TABLE {
                doc /* {{block(Composition)}} composed of a surface that holds an object or material.*/
            }
            TANK {
                doc /* {{block(Composition)}} composed of a receptacle or container that holds material.*/
            }
            TENSIONER {
                doc /* {{block(Composition)}} composed of a mechanism that provides or applies a stretch or strain to another mechanism.*/
            }
            TRANSFORMER {
                doc /* {{block(Composition)}} composed of a mechanism that transforms electric energy from a source to a secondary circuit.*/
            }
            VALVE {
                doc /* {{block(Composition)}} composed of a mechanism that halts or controls the flow of a liquid, gas, or other material through a passage, pipe, inlet, or outlet.*/
            }
            VAT {
                doc /* {{block(Composition)}} composed of a container for liquid or powdered materials.*/
            }
            WATER {
                doc /* {{block(Composition)}} composed of a fluid.*/
            }
            WIRE {
                doc /* {{block(Composition)}} composed of a string like piece or filament of relatively rigid or flexible material provided in a variety of diameters.*/
            }
            WORKPIECE {
                doc /* {{block(Composition)}} composed of an object or material on which a form of work is performed.*/
            }
            COOLING_TOWER {
                doc /* {{block(Composition)}} composed of a heat exchange system that uses a fluid to transfer heat to the atmosphere.*/
            }
            POT {
                doc /* {{block(Composition)}} composed of a tool storage location associated with a {{block(ToolMagazine)}} or {{block(AutomaticToolChanger)}}.*/
            }
            STATION {
                doc /* {{block(Composition)}} composed of a storage or mounting location for a tool associated with a {{block(Turret)}}, {{block(GangToolBar)}}, or {{block(ToolRack)}}.*/
            }
            TRANSFER_ARM {
                doc /* {{block(Composition)}} composed of a mechanism that physically moves a tool from one location to another.*/
            }
            TRANSFER_POT {
                doc /* {{block(Pot)}} for a tool awaiting transfer from a {{block(ToolMagazine)}} to {{term(spindle)}} or {{block(Turret)}}.*/
            }
            RETURN_POT {
                doc /* {{block(Pot)}} for a tool removed from {{term(spindle)}} or {{block(Turret)}} and awaiting for return to a {{block(ToolMagazine)}}.*/
            }
            STAGING_POT {
                doc /* {{block(Pot)}} for a tool awaiting transfer to a {{block(ToolMagazine)}} or {{block(Turret)}} from outside of the piece of equipment.*/
            }
            REMOVAL_POT {
                doc /* {{block(Pot)}} for a tool to be removed from a {{block(ToolMagazine)}} or {{block(Turret)}} to a location outside of the piece of equipment.*/
            }
            EXPIRED_POT {
                doc /* {{block(Pot)}} for a tool that is no longer usable for removal from a {{block(ToolMagazine)}} or {{block(Turret)}}.*/
            }
        }
        enum def CountDirectionTypeEnum {
            doc /* Enumeration for countDirection types.*/
            UP {
                doc /* tool life counts up from zero to the maximum.*/
            }
            DOWN {
                doc /* tool life counts down from the maximum to zero.*/
            }
        }
        enum def ApplicationTypeEnum {
            DESIGN {
                doc /* computer aided design files or drawings.*/
            }
            DATA {
                doc /* generic data.*/
            }
            DOCUMENTATION {
                doc /* documentation regarding a category of file.*/
            }
            INSTRUCTIONS {
                doc /* user instructions regarding the execution of a task.*/
            }
            LOG {
                doc /* data related to the history of a machine or process.*/
            }
            PRODUCTION_PROGRAM {
                doc /* machine instructions to perform a process.*/
            }
        }
        enum def FormEnum {
            BAR;
            SHEET;
            BLOCK;
            CASTING;
            POWDER;
            LIQUID;
            GEL;
            FILAMENT;
            GAS;
        }
        enum def CompositionStateVerticalEnum {
            UP {
                doc /* position of the {{block(Composition)}} element is oriented in an upward direction to the point of a positive confirmation.*/
            }
            DOWN {
                doc /* position of the {{block(Composition)}} element is oriented in a downward direction to the point of a positive confirmation.*/
            }
            TRANSITIONING {
                doc 
                /* position of the {{block(Composition)}} element is not oriented in an upward direction to the point of a positive confirmation and is not oriented in a downward direction to the point of a positive confirmation. 
                 *
                 * It is in an intermediate position.*/
            }
        }
        enum def RequestStateEnum {
            NOT_READY {
                doc /* {{term(requester)}} is not ready to make a {{term(request)}}.*/
            }
            READY {
                doc /* {{term(requester)}} is prepared to make a {{term(request)}}, but no {{term(request)}} for service is required.*/
            }
            ACTIVE {
                doc /* {{term(requester)}} has initiated a {{term(request)}} for a service and the service has not yet been completed by the {{term(responder)}}.*/
            }
            FAIL {
                doc /* {{term(requester)}} has detected a failure condition.*/
            }
        }
        enum def ResponseStateEnum {
            NOT_READY {
                doc /* {{term(responder)}} is not ready to perform a service.*/
            }
            READY {
                doc /* {{term(responder)}} is prepared to react to a {{term(request)}}, but no {{term(request)}} for service has been detected.*/
            }
            ACTIVE {
                doc 
                /* {{term(responder)}} has detected and accepted a {{term(request)}} for a service and is in the process of performing the service, but the service has not yet
                 * been completed.*/
            }
            COMPLETE {
                doc /* {{term(responder)}} has completed the actions required to perform the service.*/
            }
            FAIL {
                doc /* {{term(responder)}} has detected a failure condition.*/
            }
        }
        enum def SpindleInterlockEnum {
            ACTIVE {
                doc /* power has been removed and the spindle cannot be operated.*/
            }
            INACTIVE {
                doc /* spindle has not been deactivated.*/
            }
        }
        enum def AxisInterlockEnum {
            ACTIVE {
                doc /* axis lockout function is activated, power has been removed from the axis, and the axis is allowed to move freely.*/
            }
            INACTIVE {
                doc /* axis lockout function has not been activated, the axis may be powered, and the axis is capable of being controlled by another component.*/
            }
        }
        enum def ChuckInterlockEnum {
            ACTIVE {
                doc /* chuck cannot be unclamped.*/
            }
            INACTIVE {
                doc /* chuck can be unclamped.*/
            }
        }
        enum def DoorStateEnum {
            OPEN {
                doc /* {{block(Door)}} is open to the point of a positive confirmation.*/
            }
            CLOSED {
                doc /* {{block(Door)}} is closed to the point of a positive confirmation.*/
            }
            UNLATCHED {
                doc 
                /* {{block(Door)}} is not closed to the point of a positive confirmation and not open to the point of a positive confirmation. 
                 *
                 * It is in an intermediate position.*/
            }
        }
        enum def EquipmentModeEnum {
            ON {
                doc /* equipment is functioning in the mode designated by the `subType`.*/
            }
            OFF {
                doc /* equipment is not functioning in the mode designated by the `subType`.*/
            }
        }
        enum def PowerStateEnum {
            ON {
                doc /* source of energy for an entity or the enabling signal providing permission for the entity to perform its function(s) is present and active.*/
            }
            OFF {
                doc /* source of energy for an entity or the enabling signal providing permission for the entity to perform its function(s) is not present or is disconnected.*/
            }
        }
        enum def ConditionStateEnum {
            Normal {
                doc /* {{term(condition state)}} that indicates operation within specified limits.*/
            }
            Warning {
                doc /* {{term(condition state)}} that requires concern and supervision and may become hazardous if no action is taken.*/
            }
            Fault {
                doc /* {{term(condition state)}} that requires intervention to continue operation to function properly.*/
            }
        }
        enum def ToolLifeEnum {
            MINUTES {
                doc 
                /* tool life measured in minutes. 
                 *
                 * All units for minimum, maximum, and nominal **MUST** be provided in minutes.*/
            }
            PART_COUNT {
                doc 
                /* tool life measured in parts. 
                 *
                 * All units for minimum, maximum, and nominal **MUST** be provided as the number of parts.*/
            }
            WEAR {
                doc 
                /* tool life measured in tool wear. 
                 *
                 * Wear **MUST** be provided in millimeters as an offset to nominal. All units for minimum, maximum, and nominal **MUST** be given as millimeter offsets as
                 * well. The standard will only consider dimensional wear at this time.*/
            }
        }
        attribute def x509 :> string {
            doc /* string that represents an `x509` data block. {{cite(ISO/IEC 9594-8:2020)}}.*/
        }
        private abstract attribute def unit :> float;
        private attribute def CUBIC_MILLIMETER :> unit {
            doc /* float that represents volume in cubic millimeter.*/
        }
        enum def OperatingModeEnum {
            AUTOMATIC {
                doc 
                /* automatically execute instructions from a recipe or program.
                 *
                 * > Note: Setpoint comes from a recipe.*/
            }
            MANUAL {
                doc 
                /* execute instructions from an external agent or person.
                 *
                 * > Note 1 to entry: Valve or switch is manipulated by an agent/person.
                 *
                 * > Note 2 to entry: Direct control of the PID output. % of the range: A user manually sets the % output, not the setpoint.*/
            }
            SEMI_AUTOMATIC {
                doc 
                /* executes a single instruction from a recipe or program.
                 *
                 * > Note 1 to entry: Setpoint is entered and fixed, but the PID is controlling.
                 *
                 * > Note 2 to entry: Still goes through the PID control system.
                 *
                 * > Note 3 to entry: Manual fixed entry from a recipe.*/
            }
        }
        attribute def int32 :> integer {
            doc /* 32-bit integer.*/
        }
        attribute def int64 :> integer {
            doc /* 64-bit integer.*/
        }
        attribute def version :> string {
            doc /* series of three numeric values, separated by a decimal point, representing a {{term(major)}}, {{term(minor)}}, and {{term(patch)}} number of the MTConnect Standard.*/
        }
        attribute def uint32 :> integer {
            doc /* 32-bit unsigned integer.*/
        }
        attribute def uint64 :> integer {
            doc /* 64-bit unsigned integer.*/
        }
        enum def ErrorCodeEnum {
            ASSET_NOT_FOUND {
                doc /* {{term(request)}} for information specifies an {{block(Asset)}} that is not recognized by the {{term(agent)}}.*/
            }
            INTERNAL_ERROR {
                doc /* {{term(agent)}} experienced an error while attempting to published the requested information.*/
            }
            INVALID_REQUEST {
                doc /* {{term(request)}} contains information that was not recognized by the {{term(agent)}}.*/
            }
            INVALID_URI {
                doc /* {{term(URI)}} provided was incorrect.*/
            }
            INVALID_XPATH {
                doc 
                /* {{term(XPath)}} identified in the {{term(request)}} for information could not be parsed correctly by the {{term(agent)}}.
                 *
                 * This could be caused by an invalid syntax or the {{term(XPath)}} did not match a valid identify for any information stored in the {{term(agent)}}. */
            }
            NO_DEVICE {
                doc /* identity of the {{block(Device)}} specified in the {{term(request)}} for information is not associated with the {{term(agent)}}.*/
            }
            OUT_OF_RANGE {
                doc /* {{term(request)}} for information specifies {{term(streaming data)}} that includes sequence number(s) for pieces of data that are beyond the end of the {{term(buffer)}}.*/
            }
            QUERY_ERROR {
                doc 
                /* {{term(agent)}} was unable to interpret the query.
                 *
                 * The query parameters do not contain valid values or include an invalid parameter.*/
            }
            TOO_MANY {
                doc 
                /* `count` parameter provided in the {{term(request)}} for information requires either of the following:
                 *
                 * * {{term(streaming data)}} that includes more pieces of data than the {{term(agent)}} is capable of organizing in an {{term(MTConnectStreams Response Document)}}. 
                 *
                 * * {{block(Assets)}} that include more {{block(Asset)}} in an {{term(MTConnectAssets Response Document)}} than the {{term(agent)}} is capable of handling. */
            }
            UNAUTHORIZED {
                doc /* {{term(requester)}} does not have sufficient permissions to access the requested information.*/
            }
            UNSUPPORTED {
                doc /* valid {{term(request)}} was provided, but the {{term(agent)}} does not support the feature or type of {{term(request)}}.*/
            }
        }
        enum def MaintenanceListDirectionEnum {
            UP;
            DOWN;
        }
        enum def MaintenanceListIntervalEnum {
            ABSOLUTE;
            INCREMENTAL;
        }
        enum def PartCountTypeEnum {
            EACH {
                doc /* count is of individual items.*/
            }
            BATCH {
                doc /* pre-specified group of items.*/
            }
        }
        part def ControlLimitResult :> 'Observation Information Model'::Representations::DataSet {
            attribute UpperLimit [0..1] : float {
                doc 
                /* upper conformance boundary for a variable.
                 *
                 * > Note: immediate concern or action may be required.
                 *
                 */
            }
            attribute UpperWarning [0..1] : float {
                doc /* upper boundary indicating increased concern and supervision may be required.*/
            }
            attribute Nominal [0..1] : float {
                doc /* ideal or desired value for a variable.*/
            }
            attribute LowerWarning [0..1] : float {
                doc /* lower boundary indicating increased concern and supervision may be required.*/
            }
            attribute LowerLimit [0..1] : float {
                doc 
                /* lower conformance boundary for a variable.
                 *
                 * > Note: immediate concern or action may be required.
                 *
                 */
            }
        }
        part def SpecificationLimitResult :> 'Observation Information Model'::Representations::DataSet {
            attribute UpperLimit [0..1] : float {
                doc 
                /* upper conformance boundary for a variable.
                 *
                 * > Note: immediate concern or action may be required.
                 *
                 */
            }
            attribute Nominal [0..1] : float {
                doc /* ideal or desired value for a variable.*/
            }
            attribute LowerLimit [0..1] : float {
                doc 
                /* lower conformance boundary for a variable.
                 *
                 * > Note: immediate concern or action may be required.
                 *
                 */
            }
        }
        part def AlarmLimitResult :> 'Observation Information Model'::Representations::DataSet {
            attribute UpperLimit [0..1] : float {
                doc 
                /* upper conformance boundary for a variable.
                 *
                 * > Note: immediate concern or action may be required.
                 *
                 */
            }
            attribute UpperWarning [0..1] : float {
                doc /* upper boundary indicating increased concern and supervision may be required.*/
            }
            attribute LowerWarning [0..1] : float {
                doc /* lower boundary indicating increased concern and supervision may be required.*/
            }
            attribute LowerLimit [0..1] : float {
                doc 
                /* lower conformance boundary for a variable.
                 *
                 * > Note: immediate concern or action may be required.
                 *
                 */
            }
        }
        part def SensorAttachmentResult :> 'Observation Information Model'::Representations::DataSet {
            doc /**/
            attribute SensorId [1] : ID {
                doc /* identity of a sensor used to observe some measurement of an item.*/
            }
        }
        enum def AlarmSeverityEnum {
            CRITICAL;
            ERROR;
            WARNING;
            INFORMATION;
        }
        enum def AlarmStateEnum {
            INSTANT;
            ACTIVE;
            CLEARED;
        }
        enum def AlarmCodeEnum {
            CRASH {
                doc /* spindle crashed.*/
            }
            JAM {
                doc /* component jammed.*/
            }
            FAILURE {
                doc /* component failed.*/
            }
            FAULT {
                doc /* fault occurred on the component.*/
            }
            STALLED {
                doc /* component has stalled and cannot move.*/
            }
            OVERLOAD {
                doc /* component is overloaded.*/
            }
            ESTOP {
                doc /* ESTOP button was pressed.*/
            }
            MATERIAL {
                doc /* problem with the material.*/
            }
            MESSAGE {
                doc /* system message.*/
            }
            OTHER {
                doc /* alarm is not in any of the above categories.*/
            }
        }
        part def MaintenanceListResult :> 'Observation Information Model'::Representations::Table::Table {
            attribute Value [1] : float {
                doc /* current interval value of the activity.*/
            }
            attribute Interval [0..1] : MaintenanceListIntervalEnum default Interval::ABSOLUTE {
                doc /* interval of the value observed.*/
            }
            attribute NextServiceDate [0..1] : datetime {
                doc /* next date/time stamp that maintenance should be performed.*/
            }
            attribute Reset [0..1] : datetime {
                doc /* last date/time stamp of the {{term(observation)}} was reset.*/
            }
            attribute Severity [0..1] : integer {
                doc /* level of severity on a scale of 1-10.*/
            }
            attribute Direction [0..1] : MaintenanceListDirectionEnum default Direction::UP {
                doc /* direction of the value observed.*/
            }
            attribute Name [1] : string {
                doc /* identifier of the maintenance activity.*/
            }
            attribute LastServiceDate [0..1] : datetime {
                doc /* last date/time stamp that maintenance was performed.*/
            }
            constant attribute Units [0..1] :>> 'Observation Information Model'::Observation::units : UnitEnum default Units::COUNT {
                doc /* same as {{property(DataItem::units)}}. See {{package(Device Information Model)}}.*/
            }
            attribute Target [0..1] : float {
                doc /* target value of the next maintenance.*/
            }
        }
        enum def DirectionEnum {
            CLOCKWISE {
                doc /* clockwise rotation using the right-hand rule.*/
            }
            COUNTER_CLOCKWISE {
                doc /* counter-clockwise rotation using the right-hand rule.*/
            }
            POSITIVE;
            NEGATIVE;
        }
        enum def PowerStatusEnum {
            ON;
            OFF;
        }
        enum def NetworkWirelessEnum {
            YES {
                doc /**/
            }
            NO {
                doc /**/
            }
        }
        enum def ProgramLocationTypeEnum {
            LOCAL {
                doc /* managed by the controller.*/
            }
            EXTERNAL {
                doc /* not managed by the controller.*/
            }
        }
        enum def InterfaceEventEnum :> DataItemTypeEnum {
            INTERFACE_STATE {
                doc /* operational state of an {{block(Interface)}}.*/
            }
            MATERIAL_FEED {
                doc /* operating state of the service to advance material or feed product to a piece of equipment from a continuous or bulk source.*/
            }
            MATERIAL_CHANGE {
                doc /* operating state of the service to change the type of material or product being loaded or fed to a piece of equipment.*/
            }
            MATERIAL_RETRACT {
                doc /* operating state of the service to remove or retract material or product.*/
            }
            PART_CHANGE {
                doc /* operating state of the service to change the part or product associated with a piece of equipment to a different part or product.*/
            }
            MATERIAL_LOAD {
                doc /* operating state of the service to load a piece of material or product.*/
            }
            MATERIAL_UNLOAD {
                doc /* operating state of the service to unload a piece of material or product.*/
            }
            OPEN_CHUCK {
                doc /* operating state of the service to open a chuck.*/
            }
            OPEN_DOOR {
                doc /* operating state of the service to open a door.*/
            }
            CLOSE_CHUCK {
                doc /* operating state of the service to close a chuck.*/
            }
            CLOSE_DOOR {
                doc /* operating state of the service to close a door.*/
            }
        }
        enum def LeakDetectEnum {
            DETECTED {
                doc /* leak is currently being detected.*/
            }
            NOT_DETECTED {
                doc /* leak is currently not being detected.*/
            }
        }
        enum def BatteryStateEnum {
            CHARGED {
                doc /* {{block(Component)}} is at it's maximum rated charge level.*/
            }
            CHARGING {
                doc /* {{block(Component)}}'s charge is increasing.*/
            }
            DISCHARGING {
                doc /* {{block(Component)}}'s charge is decreasing.*/
            }
            DISCHARGED {
                doc /* {{block(Component)}} is at it's minimum charge level.*/
            }
        }
        attribute def binary :> integer {
            doc /* base-2 numeral system or binary numeral system represented by two digits: "0" and "1".*/
        }
        enum def SensorStateDetectEnum {
            DETECTED {
                doc /* sensor is active and the threshold has been met.*/
            }
            NOT_DETECTED {
                doc /* sensor is active and ready but the threshold has not been met.*/
            }
            UNKNOWN {
                doc 
                /* sensor is active, but the state cannot be determined.
                 *
                 * > Note: unknown covers situations where the sensor reading is unstable.*/
            }
        }
        part def FeatureMeasurementResult :> 'Observation Information Model'::Representations::Table::Table {
            private attribute MeasurementId [1] : ID {
                doc /* identifier of this measurement.*/
            }
            attribute FeaturePersistentId [1] : ID {
                doc /* {{term(UUID)}} of the feature.*/
            }
            attribute CharacteristicPersistentId [0..1] : ID {
                doc /* {{term(UUID)}} of the characteristic.*/
            }
            attribute MeasurementType [1] : string {
                doc 
                /* class of measurement being performed. {{cite(QIF 3:2018 Section 6.3)}}
                 *
                 * Examples: `POINT`, `RADIUS`, `ANGLE`, `LENGTH`, etc.*/
            }
            attribute MeasurementValue [1] : float {
                doc /* measurement based on the measurement type.*/
            }
            attribute MeasurementUnits [1] : string {
                doc /* engineering units of the measurement.*/
            }
            attribute CharacteristicStatus [0..1] : CharacteristicStatusEnum {
                doc /* pass/fail result of the measurement.*/
            }
            attribute UncertaintyType [0..1] : UncertaintyTypeEnum {
                doc /* method used to compute {{term(standard uncertainty)}}.*/
            }
            attribute Uncertainty [0..1] : float {
                doc /* {{term(uncertainty)}} specified by `UNCERTAINTY_TYPE`.*/
            }
        }
        enum def CharacteristicStatusEnum {
            PASS {
                doc /* measurement is within acceptable tolerances.*/
            }
            FAIL {
                doc /* measurement is not within acceptable tolerances.*/
            }
            REWORK {
                doc /* failed, but acceptable constraints achievable by utilizing additional manufacturing processes.*/
            }
            SYSTEM_ERROR {
                doc /* measurement is indeterminate due to an equipment failure.*/
            }
            INDETERMINATE {
                doc /* measurement cannot be determined.*/
            }
            NOT_ANALYZED {
                doc /* measurement cannot be evaluated.*/
            }
            BASIC_OR_THEORETIC_EXACT_DIMENSION {
                doc /* nominal provided without tolerance limits. {{cite(QIF 3:2018 5.10.2.6)}}*/
            }
            UNDEFINED {
                doc /* status of measurement cannot be determined.*/
            }
        }
        enum def UncertaintyTypeEnum {
            COMBINED {
                doc /* {{term(combined standard uncertainty)}}.*/
            }
            MEAN {
                doc /* {{term(standard uncertainty)}} using arithmetic mean or average the observations. {{cite(JCGM 100:2008 4.2)}}*/
            }
        }
        attribute def double :> NOT_COMPATIBLE_WITH_TEXTUAL {
            doc /* primitive type.*/
        }
        abstract attribute def Array {
            doc /* array.*/
        }
        attribute def float3d :> Array {
            doc /* array of size 3 and datatype float.*/
        }
        part def LocationAddressResult :> 'Observation Information Model'::Representations::DataSet {
            attribute GivenName [0..1] : string {
                doc /* element specifying the name used to distinguish between persons having the same surname(s) and who may have access to a particular delivery point.*/
            }
            attribute Surname [0..1] : string {
                doc /* element which identifies the family or parentage of an individual.*/
            }
            attribute Qualification [0..1] : string {
                doc /* element indicating an individual’s professional or academic qualification or rank in a professional group or society (e.g. PhD, Fellow of the Royal Society, FRS, Barrister at Law).*/
            }
            attribute NameQualifier [0..1] : string {
                doc /* element used in some countries to distinguish between persons with the same surname(s) who have similar given names or initials (e.g.III, Senior, the Third.).*/
            }
            attribute OrganizationName [0..1] : string {
                doc /* element giving the official name, the registered business name or other official designation of an organization.*/
            }
            attribute LegalStatus [0..1] : string {
                doc /* element indicating the formal registration of an organization (e.g. GmbH, Inc., Ltd.).*/
            }
            attribute OrganizationUnit [0..1] : string {
                doc /* element identifying a subdivision of an organization.*/
            }
            attribute Building [0..1] : string {
                doc /* element identifying the number or name and type of the edifice or construction in or adjacent to which a delivery point is located.*/
            }
            attribute Floor [0..1] : string {
                doc /* element indicating the floor or level on which a delivery point is located in a multi-story building.*/
            }
            attribute Door [0..1] : string {
                doc /* element indicating the apartment, room or office in, at or adjacent to which a delivery point, situated within a building, is located.*/
            }
            attribute Thoroughfare [0..1] : string {
                doc /* element which identifies the road or part of a road or other access route along which a delivery point can be accessed, either directly or via a secondary or tertiary road or access route.*/
            }
            attribute PremiseIdentifier [0..1] : string {
                doc /* element designating the area or the object on an area, adjacent to thoroughfare, in which the delivery point or delivery point access is located.*/
            }
            attribute Town [0..1] : string {
                doc /* element indicating the name of the populated place in which a delivery point is located, or the populated.*/
            }
            attribute Region [0..1] : string {
                doc /* element specifying the geographic or administrative area of the country in which the town is situated.*/
            }
            attribute District [0..1] : string {
                doc /* element indicating the name of the area within or adjacent to the town in which a delivery point is located, or via which it is accessed.*/
            }
            attribute CountryName [0..1] : string {
                doc /* element designating the country, dependency or area of geopolitical interest, in which a delivery point is located or via which the delivery point is accessed.*/
            }
            attribute CountryCode [0..1] : string {
                doc /* interest, in which a delivery point is located or via which the delivery point is accessed.*/
            }
            attribute PostCode [0..1] : string {
                doc /* element designating the code used for the sorting of mail.*/
            }
        }
        enum def PowerSourceTypeEnum {
            PRIMARY {
                doc /* main or principle.*/
            }
            SECONDARY {
                doc /* alternate or not primary.*/
            }
            STANDBY {
                doc /* held near at hand and ready for use and is uninterruptible.*/
            }
        }
        attribute def UUID :> ID {
            doc /* Universally Unique IDentifier. {{cite(IETF:RFC-4122)}}*/
        }
        part def LocationSpatialGeographicResult :> 'Observation Information Model'::Representations::DataSet {
            attribute Longitude [0..1] : DEGREE {
                doc /* geographic longitude.*/
            }
            attribute Latitude [0..1] : DEGREE {
                doc /* geographic latitude.*/
            }
            attribute Altitude [0..1] : METER {
                doc /* height relative to a reference.*/
            }
        }
        attribute def METER :> unit {
            doc /* float that represents measurement in meter.*/
        }
        enum def QualityEnum {
            VALID {
                doc /* {{term(observation)}} is valid against the MTConnect Standard.*/
            }
            UNVERIFIABLE {
                doc /* {{term(observation)}} cannot be validated.*/
            }
            INVALID {
                doc /* {{term(observation)}} is not valid against the MTConnect Standard according to the validation capabilities of the {{term(MTConnect Agent)}}.*/
            }
        }
        enum def QueryParameterEnum {
            device {
                doc /* See `device` parameter of {{block(Agent::Operation)}} types.*/
            }
            deviceType {
                doc /* See `deviceType` parameter of {{block(Agent::Operation)}} types.*/
            }
            path {
                doc /* See `path` parameter of {{block(Agent::Operation)}} types.*/
            }
            'from' {
                doc /* See `from` parameter of {{block(Agent::Operation)}} types.*/
            }
            count {
                doc /* See `count` parameter of {{block(Agent::Operation)}} types.*/
            }
            interval {
                doc /* See `interval` parameter of {{block(Agent::Operation)}} types.*/
            }
            heartbeat {
                doc /* See `heartbeat` parameter of {{block(Agent::Operation)}} types.*/
            }
        }
        enum def ScopeTypeEnum {
            ENTITY {
                doc /* scope or context is directly upon the source itself.*/
            }
            VALUE_PROPERTY {
                doc /* scope or context is upon a value property of the source.*/
            }
            PART {
                doc /* scope or context is upon a part or a child of the source.*/
            }
        }
        enum def ExceptionCodeEnum {
            TYPE_MISMATCH {
                doc 
                /* scope value type is mismatched.
                 *
                 * > Note: For example, a `string` instead of an `Enumeration` value.*/
            }
            NOT_FOUND {
                doc /* scope is missing a property or a part.*/
            }
            DEPRECATED {
                doc /* scope has been deprecated.*/
            }
            EXTENDED {
                doc /* scope is considered an extension of the MTConnect Standard.*/
            }
            OUT_OF_RANGE {
                doc /* scope is not within the expected range.*/
            }
            DUPLICATE_ENTRY {
                doc /* scope is a duplicate or has duplicate properties or parts.*/
            }
            INVALID_FORMAT {
                doc /* scope has either an invalid format or does not conform to the expected pattern.*/
            }
        }
        enum def SeverityEnum {
            FATAL {
                doc /* exception violates compliance with the MTConnect Standard and validation can no longer continue.*/
            }
            ERROR {
                doc /* exception violates compliance with the MTConnect Standard.*/
            }
            WARNING {
                doc /* exception **MAY** violate compliance with the MTConnect Standard.*/
            }
            INFO {
                doc /* exception is considered informative.*/
            }
        }
        enum def TaskStateEnum {
            INACTIVE {
                doc /* default state when the task is created and any collaborators are yet to bind to the task*/
            }
            PREPARING {
                doc /* task state when a collaborator is ready and binds itself to the task*/
            }
            COMMITTING {
                doc /* task state when all collaborators indicate that they can participate by binding to the task*/
            }
            COMMITTED {
                doc /* task state when all collaborators commit to the task*/
            }
            COMPLETE {
                doc /* task state when collaborators successfully implement the task*/
            }
            FAIL {
                doc /* task state when collaborators are unsuccessful in implementing the task*/
            }
        }
        enum def BindingStateEnum {
            INACTIVE {
                doc /* default state when the collaborator is yet to bind to a task*/
            }
            PREPARING {
                doc /* state when a collaborator is ready and expresses interest in all tasks that require its capability*/
            }
            COMMITTED {
                doc /* state when a collaborator has successfully bound itself to a task*/
            }
        }
        enum def PartIdentifierEnum {
            UNIQUE_IDENTIFIER {
                doc /* unique serialized part identifier.*/
            }
            GROUP_IDENTIFIER {
                doc /* identifier for a group of parts or a piece of raw material that will be transformed into multiple parts*/
            }
        }
        doc /**/
    }
    package Stereotypes {
        occurrence def organizer {
            doc /* element that {{termplural(organize)}} other elements of a type.*/
            private ref occurrence base_Element;
        }
        occurrence def deprecated {
            doc /* element that has been deprecated.*/
            private ref occurrence base_Element;
            private attribute version : DataTypes::string {
                doc /* version the element was deprecated in the standard.*/
            }
        }
        occurrence def extensible {
            doc /* enumeration that can be extended.*/
            private ref occurrence base_Enumeration;
        }
        occurrence def informative {
            doc /* element that is descriptive and non-normative.*/
            private ref occurrence base_Element;
        }
        occurrence def normative {
            doc /* element that has been added to the standard.*/
            private attribute introduced [1] : DataTypes::string {
                doc /* version the element was added to the standard.*/
            }
            private attribute updated [0..*] : DataTypes::string {
                doc /* version(s) the element was updated in the standard.*/
            }
            private attribute deprecated [0..1] : DataTypes::string {
                doc /* version the element was deprecated in the standard.*/
            }
        }
        occurrence def observes {
            doc /* association in which a {{term(Component)}} makes {{termplural(Observation)}} about an observable {{term(DataItem)}}.*/
            private ref occurrence base_Association;
        }
        occurrence def satisfiedBy {
            private ref occurrence base_InstanceSpecification;
            private ref occurrence satisfiedBy [0..*];
            private ref occurrence base_UseCase;
        }
        occurrence def ImplementationFormat {
            doc /* element that has format specific representation that might be different from the element's SysML representation.*/
            private ref occurrence base_Element;
            private attribute xml [0..1] : DataTypes::string;
            private attribute json [0..1] : DataTypes::string;
        }
        occurrence def valueType {
            doc /* extends `Class`to be used as a SysML `<<ValueType>>`.*/
            private ref occurrence base_Element;
        }
        occurrence def isArray {
            doc /* datatype that is an array.*/
            private attribute size [1] : DataTypes::integer;
            private ref occurrence type [0..1];
            private ref occurrence base_DataType;
        }
        occurrence def 'MTConnect Requirement' {
            private ref occurrence base_Element;
            private attribute redmine_issue [0..*] : DataTypes::string;
            private attribute simple_requirement [0..1] : DataTypes::string;
            private attribute semantic_requirement [0..1] : DataTypes::string;
        }
    }
    doc /* MTConnect Profile is a {{term(profile)}} that extends the {{term(SysML)}} metamodel for the MTConnect domain using additional data types and {{termplural(stereotype)}}.*/
}
package 'Asset Information Model' {
    abstract part def Asset :> Glossary::'MTConnect Terms'::Asset {
        doc /* abstract {{term(Asset)}}. */
        comment /* Description*/
        attribute assetId [1] : Profile::DataTypes::ID {
            doc /* unique identifier for an {{block(Asset)}}.*/
        }
        attribute deviceUuid [0..1] : Profile::DataTypes::UUID {
            doc 
            /* associated piece of equipment's {{term(UUID)}} that supplied the {{block(Asset)}}'s data.
             *
             * It references to {{property(Device::uuid)}} defined in {{package(Device Information Model)}}.*/
        }
        attribute removed [0..1] : Profile::DataTypes::boolean {
            doc /* indicator that the {{block(Asset)}} has been removed from the piece of equipment.*/
        }
        attribute timestamp [1] : Profile::DataTypes::datetime {
            doc /* time the {{block(Asset)}} data was last modified.*/
        }
        part hasConfiguration [0..1] : 'Device Information Model'::Configurations::Configuration;
        attribute hash [0..1] : Profile::DataTypes::string {
            doc /* condensed message digest from a secure one-way hash function. {{cite(FIPS PUB 180-4)}}*/
        }
        private attribute Description [0..1] : Profile::DataTypes::string {
            doc /* textual description for {{block(Asset)}}.*/
        }
        private attribute manufacturers [0..*] : Profile::DataTypes::string;
        private attribute model [0..1] : Profile::DataTypes::string;
        private attribute serialNumber [0..1] : Profile::DataTypes::string;
        private attribute station [0..1] : Profile::DataTypes::string;
        doc 
        /* It is used in the manufacturing process, but is not permanently associated with a single piece of equipment. It can be removed from the piece of equipment without compromising its function, and can be associated with other pieces of equipment during its lifecycle.
         *
         *
         * ![Asset](figures/Asset.png "Asset"){: width="0.8"}
         *
         * > Note: See {{sect(Assets Schema Diagrams)}} for XML schema.*/
    }
    connection def Assets {
        end hasAsset : Asset => target.hasAsset;
        doc /* {{block(Assets)}} groups one or more {{block(Asset)}} types. See {{package(Asset Information Model)}} for more details.*/
        end : Fundamentals::'MTConnect Protocol'::'MTConnectAssets Response Document'::MTConnectAssets;
    }
    package 'Cutting Tool' {
        part def CuttingTool :> Asset {
            doc /* {{block(Asset)}} that physically removes the material from the workpiece by shear deformation.*/
            attribute serialNumber [1] :>> 'Asset Information Model'::Asset::serialNumber : Profile::DataTypes::string {
                doc /* unique identifier for this assembly.*/
            }
            attribute toolId [1] : Profile::DataTypes::string {
                doc /* identifier for a class of cutting tools.*/
            }
            part hasCuttingToolLifeCycle [0..1] : 'Cutting Tool Life Cycle'::CuttingToolLifeCycle;
            part hasCuttingToolArchetypeReference [0..1] : 'Asset Information Model'::'Cutting Tool'::CuttingToolArchetypeReference;
            part hasCuttingToolDefinition [0..1] : 'Asset Information Model'::'Cutting Tool'::CuttingToolDefinition {
                doc /**/
            }
        }
        connection def CuttingToolLifeCycle {
            end hasCuttingToolLifeCycle : 'Cutting Tool Life Cycle'::CuttingToolLifeCycle => target.hasCuttingToolLifeCycle;
            doc /* See {{sect(CuttingToolLifeCycle)}}.*/
            end : CuttingTool;
        }
        connection def CuttingToolArchetypeReference {
            end hasCuttingToolArchetypeReference : 'Asset Information Model'::'Cutting Tool'::CuttingToolArchetypeReference => target.hasCuttingToolArchetypeReference;
            end : CuttingTool;
        }
        connection def CuttingToolDefinition {
            end hasCuttingToolDefinition : 'Asset Information Model'::'Cutting Tool'::CuttingToolDefinition => target.hasCuttingToolDefinition;
            doc /* **DEPRECATED** in *Version 1.3.0* for {{block(CuttingTool)}}.*/
            end : CuttingTool;
        }
        part def CuttingToolArchetype :> Asset {
            doc /* {{block(Asset)}} that describes the static cutting tool geometries and nominal values as one would expect from a tool catalog.*/
            attribute serialNumber [1] :>> 'Asset Information Model'::Asset::serialNumber : Profile::DataTypes::string {
                doc /* unique identifier for this assembly.*/
            }
            attribute toolId [1] : Profile::DataTypes::string {
                doc /* identifier for a class of cutting tools.*/
            }
            part hasCuttingToolDefinition [0..1] : 'Asset Information Model'::'Cutting Tool'::CuttingToolDefinition;
            part hasCuttingToolLifeCycle [0..1] : 'Cutting Tool Life Cycle'::CuttingToolLifeCycle;
        }
        connection def CuttingToolDefinition {
            end hasCuttingToolDefinition : 'Asset Information Model'::'Cutting Tool'::CuttingToolDefinition => target.hasCuttingToolDefinition;
            doc /* **DEPRECATED** in *Version 2.1.0* for {{block(CuttingToolArchetype)}}.*/
            end : CuttingToolArchetype;
        }
        connection def CuttingToolLifeCycle {
            end hasCuttingToolLifeCycle : 'Cutting Tool Life Cycle'::CuttingToolLifeCycle => target.hasCuttingToolLifeCycle;
            doc /* See {{sect(CuttingToolLifeCycle)}}.*/
            end : CuttingToolArchetype;
        }
        part def CuttingToolArchetypeReference {
            doc /* reference information about the {{property(Asset::assetId)}} and/or the URL of the data source of {{block(CuttingToolArchetype)}}.*/
            attribute source [0..1] : Profile::DataTypes::string {
                doc /* {{term(URL)}} of the {{block(CuttingToolArchetype)}} {{term(information model)}}.*/
            }
            attribute value [0..1] : Profile::DataTypes::ID {
                doc /* `assetId` of the related {{block(CuttingToolArchetype)}}.*/
            }
        }
        part def CuttingToolDefinition {
            doc /* detailed structure of the cutting tool which is static during its lifecycle. {{cite(ISO 13399)}}.*/
            attribute format [0..1] : Profile::DataTypes::FormatTypeEnum default format::XML {
                doc /* identifies the expected representation of the enclosed data.*/
            }
            attribute value [0..*] : Profile::DataTypes::string {
                doc /* text of the {{block(CuttingToolDefinition)}} in format defined by {{property(CuttingToolDefinition::format)}}.*/
            }
        }
        connection def CutterStatus {
            end hasCutterStatus : 'Cutting Tool Life Cycle'::Status => target.hasCutterStatus;
            doc 
            /* {{block(CutterStatus)}} provides the status of the assembly and {{term(organize)}} one or more {{block(Status)}} entities. See {{sect(Status)}}.
             *
             * The following combinations of {{block(Status)}} entities **MUST NOT** occur for a {{block(CutterStatus)}}:
             *
             * * `NEW` **MUST NOT** be used with `USED`, `RECONDITIONED`, or `EXPIRED`.
             *
             * * `UNKNOWN` **MUST NOT** be used with any other status.
             *
             * * `ALLOCATED` and `UNALLOCATED` **MUST NOT** be used together.
             *
             * * `AVAILABLE` and `UNAVAILABLE` **MUST NOT** be used together.
             *
             * * If the tool is `EXPIRED`, `BROKEN`, or `NOT_REGISTERED` it **MUST NOT** be `AVAILABLE`.
             *
             * {{block(CutterStatus)}} **MUST** be defined only for the {{block(CuttingToolLifeCycle)}} of {{block(CuttingTool)}} and **MUST NOT** be defined for the {{block(CuttingToolLifeCycle)}} of {{block(CuttingToolArchetype)}}.*/
            end : 'Cutting Item'::CuttingItem;
        }
        package 'Cutting Item' {
            part def CuttingItem {
                doc /* part of of the tool that physically removes the material from the workpiece by shear deformation.*/
                attribute Description [0..1] : Profile::DataTypes::string {
                    doc /* free-form description of the cutting item.*/
                }
                attribute grade [0..1] : Profile::DataTypes::string {
                    doc /* material composition for this cutting item.*/
                }
                attribute indices [1..*] : Profile::DataTypes::string {
                    doc 
                    /* number or numbers representing the individual cutting item or items on the tool.
                     *
                     * Indices **SHOULD** start numbering with the inserts or {{block(CuttingItem)}} furthest from the gauge line and increasing in value as the items get closer to the gauge line. Items at the same distance **MAY** be arbitrarily numbered.
                     *
                     * > Note: In {{term(XML)}}, the representation **MUST** be a single number ("1") or a comma separated set of individual elements ("1,2,3,4"), or as a inclusive range of values as in ("1-10") or any combination of ranges and numbers as in "1-4,6-10,22". There **MUST NOT** be spaces or non-integer values in the text representation.*/
                }
                attribute itemId [0..1] : Profile::DataTypes::ID {
                    doc /* manufacturer identifier of this cutting item.*/
                }
                attribute Locus [0..1] : Profile::DataTypes::string {
                    doc 
                    /* free form description of the location on the cutting tool.
                     *
                     * For clarity, the words `FLUTE`, `INSERT`, and `CARTRIDGE` **SHOULD** be used to assist in noting the location of a {{block(CuttingItem)}}. {{property(CuttingItem::Locus)}} **MAY** be any free form string, but **SHOULD** adhere to the following rules:
                     *
                     * * The location numbering **SHOULD** start at the furthest {{block(CuttingItem)}} and work it’s way back to the {{block(CuttingItem)}} closest to the gauge line.
                     *
                     * * Flutes **SHOULD** be identified as such using the word `FLUTE`:. For example: `FLUTE`: 1, `INSERT`: 2 - would indicate the first flute and the second furthest insert from the end of the tool on that flute.
                     *
                     * * Other designations such as `CARTRIDGE` **MAY** be included, but should be identified using upper case and followed by a colon (:).*/
                }
                attribute manufacturers [0..*] : Profile::DataTypes::string {
                    doc 
                    /* manufacturers of the cutting item.
                     *
                     * This will reference the tool item and adaptive items specifically. The cutting items
                     * manufacturers’ will be a property of {{block(CuttingItem)}}.
                     *
                     * > Note: In {{term(XML)}}, the representation **MUST** be a comma(,) delimited list of manufacturer names. See {{sect(CuttingItem Schema Diagrams)}}.*/
                }
                attribute ProgramToolGroup [0..1] : Profile::DataTypes::string {
                    doc /* tool group this item is assigned in the part program.*/
                }
                part hasCutterStatus [1..*] : 'Cutting Tool Life Cycle'::Status;
                part hasItemLife [0..3] : 'Asset Information Model'::'Cutting Tool'::'Cutting Item'::ItemLife {
                    doc /* The tool life measured in tool wear.*/
                }
                part hasMeasurement [0..*] : 'Cutting Tool Life Cycle'::ToolingMeasurement {
                    doc /* A collection of measurements relating to this cutting item.*/
                }
            }
            connection def ItemLife {
                end hasItemLife : 'Asset Information Model'::'Cutting Tool'::'Cutting Item'::ItemLife => target.hasItemLife;
                doc /* See {{sect(ItemLife)}}.*/
                end : CuttingItem;
            }
            connection def CuttingItems {
                end hasCuttingItem : CuttingItem => target.hasCuttingItem;
                doc /* {{block(CuttingItems)}} groups one or more {{block(CuttingItem)}} entities. See {{sect(CuttingItem)}} and {{package(Cutting Item)}} for more detail.*/
                private end : 'Cutting Tool Life Cycle'::CuttingToolLifeCycle;
                attribute count [1] : Profile::DataTypes::integer {
                    doc /* number of {{block(CuttingItem)}} organized by {{block(CuttingItems)}}.*/
                }
                part [0..*] : CuttingItem;
                part : 'Cutting Tool Life Cycle'::CuttingToolLifeCycle;
            }
            part def ItemLife {
                doc /* life of a {{block(CuttingItem)}}.*/
                attribute countDirection [1] : Profile::DataTypes::CountDirectionTypeEnum {
                    doc /* indicates if the item life counts from zero to maximum or maximum to zero.*/
                }
                attribute initial [0..1] : Profile::DataTypes::float {
                    doc /* initial life of the item when it is new.*/
                }
                attribute limit [0..1] : Profile::DataTypes::float {
                    doc /* end of life limit for this item.*/
                }
                attribute type [1] : Profile::DataTypes::ToolLifeEnum {
                    doc /* type of item life being accumulated.*/
                }
                attribute warning [0..1] : Profile::DataTypes::float {
                    doc /* point at which a item life warning will be raised.*/
                }
                attribute value [1] : Profile::DataTypes::float {
                    doc /* value of {{block(ItemLife)}}.*/
                }
            }
            connection def Measurements {
                end hasMeasurement : 'Cutting Tool Life Cycle'::ToolingMeasurement => target.hasMeasurement;
                doc /* {{block(Measurements)}} groups one or more {{block(Measurement)}} subtypes. See {{sect(Measurement)}}.*/
                private end : CuttingItem;
            }
            package 'Cutting Item Measurement Subtypes' {
                part def FunctionalLength :> 'Cutting Tool Life Cycle'::ToolingMeasurement {
                    doc 
                    /* distance from the gauge plane or from the end of the shank of the cutting tool, if a gauge plane does not exist, to the cutting reference point determined by the main function of the tool. 
                     *
                     * This measurement will be with reference to the cutting tool and **MUST NOT** exist without a cutting tool.*/
                    attribute code [1] :>> code : Profile::DataTypes::CodeEnum default code::LFx;
                    attribute units [1] :>> units : Profile::DataTypes::UnitEnum default units::MILLIMETER;
                }
                part def CuttingReferencePoint :> 'Cutting Tool Life Cycle'::ToolingMeasurement {
                    doc /* theoretical sharp point of the cutting tool from which the major functional dimensions are taken.*/
                    attribute code [1] :>> code : Profile::DataTypes::CodeEnum default code::CRP;
                    attribute units [1] :>> units : Profile::DataTypes::UnitEnum default units::MILLIMETER;
                }
                part def CuttingEdgeLength :> 'Cutting Tool Life Cycle'::ToolingMeasurement {
                    doc /* theoretical length of the cutting edge of a cutting item over sharp corners.*/
                    attribute code [1] :>> code : Profile::DataTypes::CodeEnum default code::L;
                    attribute units [1] :>> units : Profile::DataTypes::UnitEnum default units::MILLIMETER;
                }
                part def DriveAngle :> 'Cutting Tool Life Cycle'::ToolingMeasurement {
                    doc /* angle between the driving mechanism locator on a tool item and the main cutting edge.*/
                    attribute code [1] :>> code : Profile::DataTypes::CodeEnum default code::DRVA;
                    attribute units [1] :>> units : Profile::DataTypes::UnitEnum default units::DEGREE;
                }
                part def FlangeDiameter :> 'Cutting Tool Life Cycle'::ToolingMeasurement {
                    doc /* dimension between two parallel tangents on the outside edge of a flange.*/
                    attribute code [1] :>> code : Profile::DataTypes::CodeEnum default code::DF;
                    attribute units [1] :>> units : Profile::DataTypes::UnitEnum default units::MILLIMETER;
                }
                part def FunctionalWidth :> 'Cutting Tool Life Cycle'::ToolingMeasurement {
                    doc /* distance between the cutting reference point and the rear backing surface of a turning tool or the axis of a boring bar.*/
                    attribute code [1] :>> code : Profile::DataTypes::CodeEnum default code::WF;
                    attribute units [1] :>> units : Profile::DataTypes::UnitEnum default units::MILLIMETER;
                }
                part def IncribedCircleDiameter :> 'Cutting Tool Life Cycle'::ToolingMeasurement {
                    doc /* diameter of a circle to which all edges of a equilateral and round regular insert are tangential.*/
                    attribute code [1] :>> code : Profile::DataTypes::CodeEnum default code::IC;
                    attribute units [1] :>> units : Profile::DataTypes::UnitEnum default units::MILLIMETER;
                }
                part def PointAngle :> 'Cutting Tool Life Cycle'::ToolingMeasurement {
                    doc /* angle between the major cutting edge and the same cutting edge rotated by 180 degrees about the tool axis.*/
                    attribute code [1] :>> code : Profile::DataTypes::CodeEnum default code::SIG;
                    attribute units [1] :>> units : Profile::DataTypes::UnitEnum default units::DEGREE;
                }
                part def ToolCuttingEdgeAngle :> 'Cutting Tool Life Cycle'::ToolingMeasurement {
                    doc /* angle between the tool cutting edge plane and the tool feed plane measured in a plane parallel the xy-plane.*/
                    attribute code [1] :>> code : Profile::DataTypes::CodeEnum default code::KAPR;
                    attribute units [1] :>> units : Profile::DataTypes::UnitEnum default units::DEGREE;
                }
                part def ToolLeadAngle :> 'Cutting Tool Life Cycle'::ToolingMeasurement {
                    doc /* angle between the tool cutting edge plane and a plane perpendicular to the tool feed plane measured in a plane parallel the xy-plane.*/
                    attribute code [1] :>> code : Profile::DataTypes::CodeEnum default code::PSIR;
                    attribute units [1] :>> units : Profile::DataTypes::UnitEnum default units::DEGREE;
                }
                part def ToolOrientation :> 'Cutting Tool Life Cycle'::ToolingMeasurement {
                    doc 
                    /* angle of the tool with respect to the workpiece for a given process. 
                     *
                     * The value is application specific.*/
                    attribute code [1] :>> code : Profile::DataTypes::CodeEnum default code::'N/A';
                    attribute units [1] :>> units : Profile::DataTypes::UnitEnum default units::DEGREE;
                }
                part def StepDiameterLength :> 'Cutting Tool Life Cycle'::ToolingMeasurement {
                    doc /* length of a portion of a stepped tool that is related to a corresponding cutting diameter measured from the cutting reference point of that cutting diameter to the point on the next cutting edge at which the diameter starts to change.*/
                    attribute code [1] :>> code : Profile::DataTypes::CodeEnum default code::SDLx;
                    attribute units [1] :>> units : Profile::DataTypes::UnitEnum default units::MILLIMETER;
                }
                part def StepIncludedAngle :> 'Cutting Tool Life Cycle'::ToolingMeasurement {
                    doc /* angle between a major edge on a step of a stepped tool and the same cutting edge rotated 180 degrees about its tool axis.*/
                    attribute code [1] :>> code : Profile::DataTypes::CodeEnum default code::STAx;
                    attribute units [1] :>> units : Profile::DataTypes::UnitEnum default units::DEGREE;
                }
                part def WiperEdgeLength :> 'Cutting Tool Life Cycle'::ToolingMeasurement {
                    doc /* measure of the length of a wiper edge of a cutting item.*/
                    attribute code [1] :>> code : Profile::DataTypes::CodeEnum default code::BS;
                    attribute units [1] :>> units : Profile::DataTypes::UnitEnum default units::MILLIMETER;
                }
                part def CuttingDiameter :> 'Cutting Tool Life Cycle'::ToolingMeasurement {
                    doc 
                    /* diameter of a circle on which the defined point Pk located on this cutting tool. 
                     *
                     * The normal of the machined peripheral surface points towards the axis of the cutting tool.*/
                    attribute code [1] :>> code : Profile::DataTypes::CodeEnum default code::DCx;
                    attribute units [1] :>> units : Profile::DataTypes::UnitEnum default units::MILLIMETER;
                }
                part def CuttingHeight :> 'Cutting Tool Life Cycle'::ToolingMeasurement {
                    doc /* distance from the basal plane of the tool item to the cutting point.*/
                    attribute code [1] :>> code : Profile::DataTypes::CodeEnum default code::HF;
                    attribute units [1] :>> units : Profile::DataTypes::UnitEnum default units::MILLIMETER;
                }
                part def CornerRadius :> 'Cutting Tool Life Cycle'::ToolingMeasurement {
                    doc /* nominal radius of a rounded corner measured in the X Y-plane.*/
                    attribute code [1] :>> code : Profile::DataTypes::CodeEnum default code::RE;
                    attribute units [1] :>> units : Profile::DataTypes::UnitEnum default units::MILLIMETER;
                }
                part def Weight :> 'Cutting Tool Life Cycle'::ToolingMeasurement {
                    doc 
                    /* total weight of the cutting tool in grams. 
                     *
                     * The force exerted by the mass of the cutting tool.*/
                    attribute code [1] :>> code : Profile::DataTypes::CodeEnum default code::WT;
                    attribute units [1] :>> units : Profile::DataTypes::UnitEnum default units::__unnamed1() {
                        calc __unnamed1 {
                            rep language "English" /* GRAM*/
                        }
                    }
                }
                part def ChamferFlatLength :> 'Cutting Tool Life Cycle'::ToolingMeasurement {
                    doc /* flat length of a chamfer.*/
                    attribute code [1] :>> code : Profile::DataTypes::CodeEnum default code::BCH;
                    attribute units [1] :>> units : Profile::DataTypes::UnitEnum default units::MILLIMETER;
                }
                part def ChamferWidth :> 'Cutting Tool Life Cycle'::ToolingMeasurement {
                    doc /* width of the chamfer.*/
                    attribute code [1] :>> code : Profile::DataTypes::CodeEnum default code::CHW;
                    attribute units [1] :>> units : Profile::DataTypes::UnitEnum default units::MILLIMETER;
                }
                part def InsertWidth :> 'Cutting Tool Life Cycle'::ToolingMeasurement {
                    doc /* W1 is used for the insert width when an inscribed circle diameter is not practical.*/
                    attribute code [1] :>> code : Profile::DataTypes::CodeEnum default code::W1;
                    attribute units [1] :>> units : Profile::DataTypes::UnitEnum default units::MILLIMETER;
                }
                doc 
                /* This section lists the {{block(Measurement)}} subtypes for {{block(CuttingItem)}}.
                 *
                 * These {{block(Measurement)}} subtypes for {{block(CuttingItem)}} are specific to an individual {{block(CuttingItem)}} and **MUST NOT** be used for the {{block(Measurement)}} pertaining to an assembly. Figures below will be used to for reference for the {{block(CuttingItem)}} specific {{block(Measurement)}} types.
                 *
                 * ![Cutting Tool](figures/Cutting%20Tool.png "Cutting Tool"){: width="0.8"}
                 *
                 * ![Cutting Item](figures/Cutting%20Item.png "Cutting Item"){: width="0.8"}
                 *
                 * ![Cutting Item Measurement](figures/Cutting%20Item%20Measurement.png "Cutting Item Measurement"){: width="0.8"}
                 *
                 * ![Cutting Item Drive Angle](figures/Cutting%20Item%20Drive%20Angle.png "Cutting Item Drive Angle"){: width="0.8"}*/
            }
            doc 
            /* A {{block(CuttingItem)}} is the portion of the tool that physically removes the material from the workpiece by shear deformation. The cutting item can be either a single piece of material attached to the {{block(CuttingTool)}} or it can be one or more separate pieces of material attached to the {{block(CuttingTool)}} using a permanent or removable attachment.  A {{block(CuttingItem)}} can be comprised of one or more cutting edges. Cutting items include: replaceable inserts, brazed tips and the cutting portions of solid {{block(CuttingTools)}}.
             *
             * MTConnect Standard considers {{block(CuttingItems)}} as part of the {{block(CuttingTool)}}.  A {{block(CuttingItems)}} **MUST NOT** exist in MTConnect unless it is attached to a {{block(CuttingTool)}}.  Some of the measurements, such as {{block(FunctionalLength)}}, **MUST** be made with reference to the entire {{block(CuttingTool)}} to be meaningful.
             *
             * ![CuttingItem](figures/CuttingItem.png "CuttingItem"){: width="0.8"}
             *
             * > Note: See {{sect(CuttingItem Schema Diagrams)}} for XML schema.*/
        }
        package 'Cutting Tool Measurement Subtypes' {
            part def BodyDiameterMax :> 'Cutting Tool Life Cycle'::ToolingMeasurement {
                doc /* largest diameter of the body of a tool item.*/
                attribute code [1] :>> code : Profile::DataTypes::CodeEnum default code::BDX;
                attribute units [1] :>> units : Profile::DataTypes::UnitEnum default units::MILLIMETER;
            }
            part def BodyLengthMax :> 'Cutting Tool Life Cycle'::ToolingMeasurement {
                doc /* distance measured along the X axis from that point of the item closest to the workpiece, including the cutting item for a tool item but excluding a protruding locking mechanism for an adaptive item, to either the front of the flange on a flanged body or the beginning of the connection interface feature on the machine side for cylindrical or prismatic shanks.*/
                attribute code [1] :>> code : Profile::DataTypes::CodeEnum default code::LBX;
                attribute units [1] :>> units : Profile::DataTypes::UnitEnum default units::MILLIMETER;
            }
            part def DepthOfCutMax :> 'Cutting Tool Life Cycle'::ToolingMeasurement {
                doc /* maximum engagement of the cutting edge or edges with the workpiece measured perpendicular to the feed motion.*/
                attribute code [1] :>> code : Profile::DataTypes::CodeEnum default code::APMX;
                attribute units [1] :>> units : Profile::DataTypes::UnitEnum default units::MILLIMETER;
            }
            part def CuttingDiameterMax :> 'Cutting Tool Life Cycle'::ToolingMeasurement {
                doc 
                /* maximum diameter of a circle on which the defined point Pk of each of the master inserts is located on a tool item. 
                 *
                 * The normal of the machined peripheral surface points towards the axis of the cutting tool.*/
                attribute code [1] :>> code : Profile::DataTypes::CodeEnum default code::DC;
                attribute units [1] :>> units : Profile::DataTypes::UnitEnum default units::MILLIMETER;
            }
            part def FlangeDiameterMax :> 'Cutting Tool Life Cycle'::ToolingMeasurement {
                doc /* dimension between two parallel tangents on the outside edge of a flange.*/
                attribute code [1] :>> code : Profile::DataTypes::CodeEnum default code::DF;
                attribute units [1] :>> units : Profile::DataTypes::UnitEnum default units::MILLIMETER;
            }
            part def OverallToolLength :> 'Cutting Tool Life Cycle'::ToolingMeasurement {
                doc /* largest length dimension of the cutting tool including the master insert where applicable.*/
                attribute code [1] :>> code : Profile::DataTypes::CodeEnum default code::OAL;
                attribute units [1] :>> units : Profile::DataTypes::UnitEnum default units::MILLIMETER;
            }
            part def ShankDiameter :> 'Cutting Tool Life Cycle'::ToolingMeasurement {
                doc /* dimension of the diameter of a cylindrical portion of a tool item or an adaptive item that can participate in a connection.*/
                attribute code [1] :>> code : Profile::DataTypes::CodeEnum default code::DMM;
                attribute units [1] :>> units : Profile::DataTypes::UnitEnum default units::MILLIMETER;
            }
            part def ShankHeight :> 'Cutting Tool Life Cycle'::ToolingMeasurement {
                doc /* dimension of the height of the shank.*/
                attribute code [1] :>> code : Profile::DataTypes::CodeEnum default code::H;
                attribute units [1] :>> units : Profile::DataTypes::UnitEnum default units::MILLIMETER;
            }
            part def ShankLength :> 'Cutting Tool Life Cycle'::ToolingMeasurement {
                doc /* dimension of the length of the shank.*/
                attribute code [1] :>> code : Profile::DataTypes::CodeEnum default code::LS;
                attribute units [1] :>> units : Profile::DataTypes::UnitEnum default units::MILLIMETER;
            }
            part def UsableLengthMax :> 'Cutting Tool Life Cycle'::ToolingMeasurement {
                doc /* maximum length of a cutting tool that can be used in a particular cutting operation including the non-cutting portions of the tool.*/
                attribute code [1] :>> code : Profile::DataTypes::CodeEnum default code::LUX;
                attribute units [1] :>> units : Profile::DataTypes::UnitEnum default units::MILLIMETER;
            }
            part def ProtrudingLength :> 'Cutting Tool Life Cycle'::ToolingMeasurement {
                doc /* dimension from the yz-plane to the furthest point of the tool item or adaptive item measured in the -X direction.*/
                attribute code [1] :>> code : Profile::DataTypes::CodeEnum default code::LPR;
                attribute units [1] :>> units : Profile::DataTypes::UnitEnum default units::MILLIMETER;
            }
            part def FunctionalLength :> 'Cutting Tool Life Cycle'::ToolingMeasurement {
                doc 
                /* distance from the gauge plane or from the end of the shank to the furthest point on the tool, if a gauge plane does not exist, to the cutting reference point determined by the main function of the tool.
                 *
                 * The {{block(CuttingTool)}} functional length will be the length of the entire tool, not a single cutting item. Each {{block(CuttingItem)}} can have an independent {{block(FunctionalLength)}} represented in its measurements. */
                attribute code [1] :>> code : Profile::DataTypes::CodeEnum default code::LF;
                attribute units [1] :>> units : Profile::DataTypes::UnitEnum default units::MILLIMETER;
            }
            part def Weight :> 'Cutting Tool Life Cycle'::ToolingMeasurement {
                doc 
                /* total weight of the cutting tool in grams. 
                 *
                 * The force exerted by the mass of the cutting tool.*/
                attribute code [1] :>> code : Profile::DataTypes::CodeEnum default code::WT;
                attribute units [1] :>> units : Profile::DataTypes::UnitEnum default units::__unnamed2() {
                    calc __unnamed2 {
                        rep language "English" /* GRAM*/
                    }
                }
            }
            doc 
            /* This section lists the {{block(Measurement)}} subtypes for {{block(CuttingTool)}}.
             *
             * These {{block(Measurement)}} subtypes for {{block(CuttingTool)}} are specific to the entire assembly and **MUST NOT** be used for the {{block(Measurement)}} pertaining to a {{block(CuttingItem)}}. {{figure(Cutting Tool Measurement 1)}} and {{figure(Cutting Tool Measurement 2)}} will be used to reference the assembly specific {{block(Measurement)}} subtypes.
             *
             * ![Cutting Tool Measurement 1](figures/Cutting%20Tool%20Measurement%201.png "Cutting Tool Measurement 1"){: width="0.8"}
             *
             * ![Cutting Tool Measurement 2](figures/Cutting%20Tool%20Measurement%202.png "Cutting Tool Measurement 2"){: width="0.8"}
             */
        }
        package 'Cutting Tool Life Cycle' {
            part def CuttingToolLifeCycle {
                doc 
                /* data regarding the application or use of the tool.
                 *
                 * This data is provided by various pieces of equipment (i.e. machine tool, presetter) and statistical process control applications. Life cycle data will not remain static, but will change periodically when a tool is used or measured.*/
                attribute ConnectionCodeMachineSide [0..1] : Profile::DataTypes::string {
                    doc /* identifier for the capability to connect any component of the cutting tool together, except Assembly Items, on the machine side. Code: `CCMS`*/
                }
                attribute ProgramToolGroup [0..1] : Profile::DataTypes::string {
                    doc /* tool group this tool is assigned in the part program.*/
                }
                attribute ProgramToolNumber [0..1] : Profile::DataTypes::string {
                    doc /* number of the tool as referenced in the part program.*/
                }
                part hasProcessFeedRate [0..1] : 'Asset Information Model'::'Cutting Tool'::'Cutting Tool Life Cycle'::ProcessFeedRate;
                part hasToolLife [0..3] : 'Asset Information Model'::'Cutting Tool'::'Cutting Tool Life Cycle'::ToolLife;
                part hasProcessSpindleSpeed [0..1] : 'Asset Information Model'::'Cutting Tool'::'Cutting Tool Life Cycle'::ProcessSpindleSpeed;
                part hasCutterStatus [1..*] : Status;
                part hasCuttingItem [0..*] : 'Cutting Item'::CuttingItem;
                part hasMeasurement [0..*] : ToolingMeasurement;
                part hasReconditionCount [0..1] : 'Asset Information Model'::'Cutting Tool'::'Cutting Tool Life Cycle'::ReconditionCount;
                part hasLocation [0..1] : 'Asset Information Model'::'Cutting Tool'::'Cutting Tool Life Cycle'::Location;
            }
            connection def CutterStatus {
                end hasCutterStatus : Status => target.hasCutterStatus;
                doc 
                /* {{block(CutterStatus)}} provides the status of the assembly and {{term(organize)}} one or more {{block(Status)}} entities. See {{sect(Status)}}.
                 *
                 * The following combinations of {{block(Status)}} entities **MUST NOT** occur for a {{block(CutterStatus)}}:
                 *
                 * * `NEW` **MUST NOT** be used with `USED`, `RECONDITIONED`, or `EXPIRED`.
                 *
                 * * `UNKNOWN` **MUST NOT** be used with any other status.
                 *
                 * * `ALLOCATED` and `UNALLOCATED` **MUST NOT** be used together.
                 *
                 * * `AVAILABLE` and `UNAVAILABLE` **MUST NOT** be used together.
                 *
                 * * If the tool is `EXPIRED`, `BROKEN`, or `NOT_REGISTERED` it **MUST NOT** be `AVAILABLE`.*/
                end : CuttingToolLifeCycle;
            }
            connection def ReconditionCount {
                end hasReconditionCount : 'Asset Information Model'::'Cutting Tool'::'Cutting Tool Life Cycle'::ReconditionCount => target.hasReconditionCount;
                doc /* See {{sect(ReconditionCount)}}.*/
                end : CuttingToolLifeCycle;
            }
            connection def ProcessSpindleSpeed {
                end hasProcessSpindleSpeed : 'Asset Information Model'::'Cutting Tool'::'Cutting Tool Life Cycle'::ProcessSpindleSpeed => target.hasProcessSpindleSpeed;
                doc /* See {{sect(ProcessSpindleSpeed)}}.*/
                end : CuttingToolLifeCycle;
            }
            connection def ProcessFeedRate {
                end hasProcessFeedRate : 'Asset Information Model'::'Cutting Tool'::'Cutting Tool Life Cycle'::ProcessFeedRate => target.hasProcessFeedRate;
                doc /* See {{sect(ProcessFeedRate)}}.*/
                end : CuttingToolLifeCycle;
            }
            connection def ToolLife {
                end hasToolLife : 'Asset Information Model'::'Cutting Tool'::'Cutting Tool Life Cycle'::ToolLife => target.hasToolLife;
                doc /* See {{sect(ToolLife)}}.*/
                end : CuttingToolLifeCycle;
            }
            connection def Location {
                end hasLocation : 'Asset Information Model'::'Cutting Tool'::'Cutting Tool Life Cycle'::Location => target.hasLocation;
                doc /* See {{sect(Location)}} for more detail.*/
                end : CuttingToolLifeCycle;
            }
            connection def Measurements {
                end hasMeasurement : ToolingMeasurement => target.hasMeasurement;
                doc /* {{block(Measurements)}} groups one or more {{block(Measurement)}} subtypes. See {{sect(Measurement)}}.*/
                end : CuttingToolLifeCycle;
            }
            part def ToolLife {
                doc /* cutting tool life as related to the assembly.*/
                comment /* Description*/
                attribute countDirection [1] : Profile::DataTypes::CountDirectionTypeEnum {
                    doc /* indicates if the tool life counts from zero to maximum or maximum to zero.*/
                }
                attribute initial [0..1] : Profile::DataTypes::float {
                    doc /* initial life of the tool when it is new.*/
                }
                attribute limit [0..1] : Profile::DataTypes::float {
                    doc /* end of life limit for the tool.*/
                }
                attribute type [1] : Profile::DataTypes::ToolLifeEnum {
                    doc /* type of tool life being accumulated.*/
                }
                attribute warning [0..1] : Profile::DataTypes::float {
                    doc /* point at which a tool life warning will be raised.*/
                }
                attribute value [1] : Profile::DataTypes::float {
                    doc /* value of {{block(ToolLife)}}.*/
                }
                doc /* {{block(ToolLife)}} **MUST** be defined only for the {{block(CuttingToolLifeCycle)}} of {{block(CuttingTool)}} and **MUST NOT** be defined for the {{block(CuttingToolLifeCycle)}} of {{block(CuttingToolArchetype)}}.*/
            }
            part def Location {
                doc 
                /* location of the pot or spindle the cutting tool currently resides in.
                 *
                 * If {{property(Location::negativeOverlap)}} or {{property(Location::positiveOverlap)}} is provided, the tool reserves additional locations on either side, otherwise if they are not given, no additional locations are required for this tool.
                 *
                 * If the pot occupies the first or last location, a rollover to the beginning or the end of the indexable values may occur. For example, if there are 64 pots and the tool is in pot 64 with a {{property(Location::positiveOverlap)}} of 1, the first pot **MAY** be occupied as well.*/
                comment /* Description*/
                attribute negativeOverlap [0..1] : Profile::DataTypes::integer {
                    doc /* number of locations at lower index values from this location.*/
                }
                attribute positiveOverlap [0..1] : Profile::DataTypes::integer {
                    doc /* number of locations at higher index value from this location.*/
                }
                attribute type [1] : Profile::DataTypes::LocationTypeEnum {
                    doc 
                    /* type of location being identified. 
                     *
                     * When a `POT` or `STATION` type is used, {{property(Location::value)}}**MUST** be a numeric value.*/
                }
                attribute turret [0..1] : Profile::DataTypes::string {
                    doc /* turret associated with a tool.*/
                }
                attribute toolMagazine [0..1] : Profile::DataTypes::string {
                    doc /* tool magazine associated with a tool.*/
                }
                attribute toolBar [0..1] : Profile::DataTypes::string {
                    doc /* tool bar associated with a tool.*/
                }
                attribute toolRack [0..1] : Profile::DataTypes::string {
                    doc /* tool rack associated with a tool.*/
                }
                attribute automaticToolChanger [0..1] : Profile::DataTypes::string {
                    doc /* automatic tool changer associated with a tool.*/
                }
                attribute value [0..1] : Profile::DataTypes::string;
                doc /* {{block(Location)}} **MUST** be defined only for the {{block(CuttingToolLifeCycle)}} of {{block(CuttingTool)}} and **MUST NOT** be defined for the {{block(CuttingToolLifeCycle)}} of {{block(CuttingToolArchetype)}}.*/
            }
            part def ReconditionCount {
                doc /* number of times the cutter has been reconditioned.*/
                attribute maximumCount [0..1] : Profile::DataTypes::integer {
                    doc /* maximum number of times the tool may be reconditioned.*/
                }
                attribute value [0..1] : Profile::DataTypes::integer {
                    doc /* {{property(ReconditionCount::value)}} **MUST** be provided for {{block(CuttingTool::CuttingToolLifeCycle)}} and **MUST NOT** be provided for the {{block(CuttingToolArchetype::CuttingToolLifeCycle)}}.*/
                }
            }
            part def ProcessSpindleSpeed {
                doc 
                /* constrained process spindle speed for the tool in revolutions/minute.
                 *
                 * The {{property(ProcessSpindleSpeed::value)}} **MAY** contain the nominal process target spindle speed if available. If {{block(ProcessSpindleSpeed)}} is provided, at least one value of {{property(ProcessSpindleSpeed::maximum)}}, {{property(ProcessSpindleSpeed::nominal)}}, or {{property(ProcessSpindleSpeed::minimum)}} **MUST** be specified.*/
                attribute maximum [0..1] : Profile::DataTypes::float {
                    doc /* upper bound for the tool’s target spindle speed.*/
                }
                attribute minimum [0..1] : Profile::DataTypes::float {
                    doc /* lower bound for the tools spindle speed.*/
                }
                attribute nominal [0..1] : Profile::DataTypes::float {
                    doc /* nominal speed the tool is designed to operate at.*/
                }
                attribute value [0..1] : Profile::DataTypes::float;
            }
            part def ProcessFeedRate {
                doc 
                /* constrained process feed rate for the tool in mm/s.
                 *
                 * The {{property(ProcessFeedRate::value)}} **MAY** contain the nominal process target feed rate if available. If {{block(ProcessFeedRate)}} is provided, at least one value of {{property(ProcessFeedRate::maximum)}}, {{property(ProcessFeedRate::nominal)}}, or {{property(ProcessFeedRate::minimum)}} **MUST** be specified.*/
                attribute maximum [0..1] : Profile::DataTypes::float {
                    doc /* upper bound for the tool’s process target feedrate.*/
                }
                attribute minimum [0..1] : Profile::DataTypes::float {
                    doc /* lower bound for the tool's feedrate.*/
                }
                attribute nominal [0..1] : Profile::DataTypes::float {
                    doc /* nominal feedrate the tool is designed to operate at.*/
                }
                attribute value [0..1] : Profile::DataTypes::float;
            }
            part def Status {
                doc /* status of the cutting tool.*/
                attribute value [1] : Profile::DataTypes::CutterStatusTypeEnum {
                    doc /* status value of the cutting tool.*/
                }
            }
            abstract part def ToolingMeasurement :> Pallet::Measurements::Measurement {
                doc /* constrained scalar value associated with a cutting tool.*/
                comment /* Description*/
                attribute code [0..1] : Profile::DataTypes::CodeEnum {
                    doc 
                    /* shop specific code for the measurement. 
                     *
                     * ISO 13399 codes **MAY** be used for these codes as well. 
                     *
                     * See {{package(Cutting Tool Measurement Subtypes)}} and {{package(Cutting Item Measurement Subtypes)}} for details on {{block(Measurement)}} types and their respective {{property(Measurement::code)}} values.*/
                }
                doc /* A {{block(Measurement)}} is specific to the tool management policy at a particular shop. The tool zero reference point or gauge line will be different depending on the particular implementation and will be assumed to be consistent within the shop. MTConnect Standard does not standardize the manufacturing process or the definition of the zero point.*/
            }
            doc 
            /* This section provides semantic information for the {{block(CuttingToolLifeCycle)}} model.
             *
             * ![CuttingToolLifeCycle](figures/CuttingToolLifeCycle.png "CuttingToolLifeCycle"){: width="0.8"}
             *
             * > Note: See {{sect(CuttingToolLifeCycle Schema Diagrams)}} for XML schema.
             */
        }
        doc 
        /* This section provides semantic information for the {{block(CuttingTool)}} and {{block(CuttingToolArchetype)}} models.
         *
         * ![CuttingTool](figures/CuttingTool.png "CuttingTool"){: width="0.8"}
         *
         * > Note: See {{sect(CuttingTool Schema Diagrams)}} for XML schema.
         */
        comment /* Cutting Tool Asset Information Model*/
        doc 
        /* There are two {{termplural(information model)}} used to represent a cutting tool, {{block(CuttingToolArchetype)}} and {{block(CuttingTool)}}. The {{block(CuttingToolArchetype)}} represents the static cutting tool geometries and nominal values as one would expect from a tool catalog and the {{block(CuttingTool)}} represents the use or application of the tool on the shop floor with actual measured values and process data. In Version 1.3.0 of the MTConnect Standard it was decided to separate out these two concerns since not all pieces of equipment will have access to both sets of information. In this way, a generic definition of the cutting tool can coexist with a specific assembly {{term(information model)}} with minimal redundancy of data.
         *
         * MTConnect Standard will adopt the ISO 13399 structure when formulating the vocabulary for Cutting Tool geometries and structure to be represented in the {{block(CuttingToolArchetype)}}. The nominal values provided in the {{block(CuttingToolLifeCycle)}} section are only concerned with two aspects of the Cutting Tool; the Cutting Tool and the cutting item. The tool item, Adaptive Item, and Assembly Item will only be covered in the {{block(CuttingToolDefinition)}} section of this document since this section contains the full ISO 13399 information about a Cutting Tool.
         *
         * ![Cutting Tool Parts](figures/Cutting%20Tool%20Parts.png "Cutting Tool Parts"){: width="0.8"}
         *
         * The {{figure(Cutting Tool Parts)}} illustrates the parts of a Cutting Tool. The Cutting Tool is the aggregate of all the components and the cutting item is the part of the tool that removes the material from the workpiece. These are the primary focus of the MTConnect Standard.
         *
         * ![Cutting Tool Composition](figures/Cutting%20Tool%20Composition.png "Cutting Tool Composition"){: width="0.8"}
         *
         * {{figure(Cutting Tool Composition)}} provides another view of the composition of a Cutting Tool. The Adaptive Items and tool items will be used for measurements, but will not be modeled as separate entities. When we are referencing the Cutting Tool we are referring to the entirety of the assembly and when we provide data regarding the cutting item we are referencing each individual item as illustrated on the left of the previous diagram.
         *
         * ![Cutting Tool, Tool Item, and Cutting Item](figures/Cutting%20Tool,%20Tool%20Item,%20and%20Cutting%20Item.png "Cutting Tool, Tool Item, and Cutting Item"){: width="0.8"}
         *
         * ![Cutting Tool, Tool Item, and Cutting Item 2](figures/Cutting%20Tool,%20Tool%20Item,%20and%20Cutting%20Item%202.png "Cutting Tool, Tool Item, and Cutting Item 2"){: width="0.8"}
         *
         *
         * {{figure(Cutting Tool, Tool Item, and Cutting Item)}} and {{figure(Cutting Tool, Tool Item, and Cutting Item 2)}} further illustrates the components of the Cutting Tool. As we compose the tool item, cutting item, Adaptive Item, we get a Cutting Tool. The tool item, Adaptive Item, and Assembly Item will only be in the {{block(CuttingToolDefinition)}} section that will contain the full ISO 13399 information. These figures also use the ISO 13399 codes for each of the measurements. These codes will be translated into the MTConnect Standard vocabulary as illustrated below. The measurements will have a maximum, minimum, and nominal value representing the tolerance of allowable values for this dimension.
         *
         * The MTConnect Standard will not define the entire geometry of the Cutting Tool, but will provide the information necessary to use the tool in the manufacturing process. Additional information can be added to the definition of the Cutting Tool by means of schema extensions.
         *
         * Additional diagrams will reference these dimensions by their codes that will be defined in the measurement tables. The codes are consistent with the codes used in ISO 13399 and have been standardized. MTConnect Standard will use the full text name for clarity in the {{termplural(response document)}}.
         *
         *
         */
    }
    package Files {
        abstract part def AbstractFile :> Asset {
            doc /* abstract {{block(Asset)}} that contains the common properties of the {{block(File)}} and {{block(FileArchetype)}} types.*/
            attribute name [1] : Profile::DataTypes::string {
                doc /* name of the file.*/
            }
            attribute mediaType [1] : Profile::DataTypes::string {
                doc /* mime type of the file.*/
            }
            attribute applicationCategory [1] : Profile::DataTypes::ApplicationCategoryEnum {
                doc /* category of application that will use this file.*/
            }
            attribute applicationType [1] : Profile::DataTypes::ApplicationTypeEnum {
                doc /* type of application that will use this file.*/
            }
            part hasFileProperty [0..*] : FileProperty;
            part hasFileComment [0..*] : FileComment;
        }
        connection def FileComments {
            end hasFileComment : FileComment => target.hasFileComment;
            doc 
            /* {{block(FileComments)}} groups one or more {{block(FileComment)}} entities for a {{block(File)}}.
             *  See {{sect(FileComment)}}.*/
            private end : AbstractFile;
        }
        connection def FileProperties {
            end hasFileProperty : FileProperty => target.hasFileProperty;
            doc 
            /* {{block(FileProperties)}} groups one or more {{block(FileProperty)}} entities for a {{block(File)}}.
             *  See {{sect(FileProperty)}}.*/
            private end : AbstractFile;
        }
        part def File :> AbstractFile {
            doc /* {{block(AbstractFile)}} type that provides information about the {{block(File)}} instance and its {{term(URL)}}.*/
            attribute size [1] : Profile::DataTypes::integer {
                doc /* size of the file in bytes.*/
            }
            attribute versionId [1] : Profile::DataTypes::string {
                doc /* version identifier of the file.*/
            }
            attribute 'state' [1] : Profile::DataTypes::FileStateEnum {
                doc /* state of the file. */
            }
            attribute Signature [0..1] : Profile::DataTypes::x509 {
                doc /* secure hash of the file.*/
            }
            attribute PublicKey [0..1] : Profile::DataTypes::x509 {
                doc /* public key used to verify the signature.*/
            }
            attribute CreationTime [1] : Profile::DataTypes::datetime {
                doc /* time the file was created.*/
            }
            attribute ModificationTime [0..1] : Profile::DataTypes::datetime {
                doc /* time the file was modified.*/
            }
            part hasLocation [1] : 'Asset Information Model'::Files::FileLocation;
            part hasDestination [0..*] : Destination;
        }
        connection def FileLocation {
            end hasLocation : 'Asset Information Model'::Files::FileLocation => target.hasLocation;
            doc /* See {{sect(FileLocation)}}.*/
            private end : File;
        }
        connection def Destinations {
            end hasDestination : Destination => target.hasDestination;
            doc /* {{block(Destinations)}} groups one or more {{block(Destination)}} entities. See {{sect(Destination)}}.*/
            private end : File;
        }
        part def FileArchetype :> AbstractFile {
            doc /* {{block(AbstractFile)}} type that provides information common to all versions of a file.*/
        }
        part def FileProperty {
            doc /* key-value pair providing additional metadata about a {{block(File)}}.*/
            attribute name [1] : Profile::DataTypes::string {
                doc /* name of the {{block(FileProperty)}}.*/
            }
            attribute value [1] : Profile::DataTypes::string {
                doc /* The value of the {{block(FileProperty)}}.*/
            }
        }
        part def FileComment {
            doc /* remark or interpretation for human interpretation associated with a {{block(File)}} or {{block(FileArchetype)}}.*/
            attribute timestamp [1] : Profile::DataTypes::datetime {
                doc /* time the comment was made.*/
            }
            attribute value [1] : Profile::DataTypes::string {
                doc /* text of the comment about the file.*/
            }
        }
        part def FileLocation {
            doc /* {{term(URL)}} reference to the file location. */
            attribute href [1] : Profile::DataTypes::xlinkhref {
                doc 
                /* {{term(URL)}} reference to the file.
                 *
                 * `href` is of type `xlink:href` from the W3C XLink specification.*/
            }
            attribute 'xlink:type' [0..1] : Profile::DataTypes::xlinktype {
                doc 
                /* type of href for the xlink href type. 
                 *
                 * **MUST** be `locator` referring to a {{term(URL)}}
                 * .*/
            }
        }
        part def Destination {
            doc /* reference to the target {{block(Device)}} for this {{block(File)}}.*/
            attribute deviceUuid [1] : Profile::DataTypes::UUID {
                doc /* `uuid` of the target device or application.*/
            }
        }
        doc 
        /* This section provides semantic information for the {{block(File)}} model.
         *
         * ![Files](figures/Files.png "Files"){: width="0.8"}
         *
         * > Note: See {{sect(File Schema Diagrams)}} for XML schema.
         */
        comment /* Files Asset Information Model*/
        doc 
        /* Manufacturing processes require various documents, programs, setup sheets, and digital media available at the device for a given process. The {{block(File)}} and {{block(FileArchetype)}} {{block(Asset)}}s provide a mechanism to communicate specific "Files" that are relevant to a process where the media is located on a server and represented by a Universal Resource Locator (URL).
         *
         * The {{block(FileArchetype)}} contains metadata common to all {{block(File)}} {{block(Asset)}}s for a certain purpose. The {{block(File)}} {{block(Asset)}} references the file specific to a given device or set of devices. The {{block(File)}} {{block(Asset)}} does not hold the contents of the file, it contains a reference to the location (URL) used to access the information. The metadata associated with the {{block(File)}} provides semantic information about the representation (mime-type) and the application associated with the {{block(File)}}. The application of the file is an extensible controlled vocabulary with common manufacturing uses provided.*/
    }
    package 'Raw Material' {
        part def RawMaterial :> Asset {
            doc /* {{block(Asset)}} that represents {{term(raw material)}}.*/
            attribute name [0..1] : Profile::DataTypes::string {
                doc 
                /* name of the {{term(raw material)}}.
                 *
                 * Examples: `Container1` and `AcrylicContainer`.*/
            }
            attribute containerType [0..1] : Profile::DataTypes::string {
                doc 
                /* type of container holding the {{term(raw material)}}. 
                 *
                 * Examples: `Pallet`, `Canister`, `Cartridge`, `Tank`, `Bin`, `Roll`, and `Spool`.*/
            }
            attribute processKind [0..1] : Profile::DataTypes::string {
                doc 
                /* ISO process type supported by this {{term(raw material)}}. 
                 *
                 * Examples include: `VAT_POLYMERIZATION`, `BINDER_JETTING`, `MATERIAL_EXTRUSION`, `MATERIAL_JETTING`, `SHEET_LAMINATION`, `POWDER_BED_FUSION` and `DIRECTED_ENERGY_DEPOSITION`.*/
            }
            attribute serialNumber [0..1] : Profile::DataTypes::string {
                doc /* serial number of the {{term(raw material)}}.*/
            }
            attribute HasMaterial [0..1] : Profile::DataTypes::boolean {
                doc /* {{block(Material)}} has existing usable volume.*/
            }
            part hasMaterial [0..1] : Material;
            attribute Form [1] : Profile::DataTypes::FormEnum {
                doc /* form of the {{term(raw material)}}.*/
            }
            attribute ManufacturingDate [0..1] : Profile::DataTypes::datetime {
                doc /* date the {{term(raw material)}} was created.*/
            }
            attribute FirstUseDate [0..1] : Profile::DataTypes::datetime {
                doc /* date {{term(raw material)}} was first used.*/
            }
            attribute LastUseDate [0..1] : Profile::DataTypes::datetime {
                doc /* date {{term(raw material)}} was last used.*/
            }
            attribute InitialVolume [0..1] : Profile::DataTypes::CUBIC_MILLIMETER {
                doc /* amount of material initially placed in {{term(raw material)}} when manufactured.*/
            }
            attribute InitialDimension [0..3] : Profile::DataTypes::MILLIMETER {
                doc /* dimension of material initially placed in {{term(raw material)}} when manufactured.*/
            }
            attribute InitialQuantity [0..1] : Profile::DataTypes::integer {
                doc /* quantity of material initially placed in {{term(raw material)}} when manufactured.*/
            }
            attribute CurrentVolume [0..1] : Profile::DataTypes::CUBIC_MILLIMETER {
                doc /* amount of material currently in {{term(raw material)}}.*/
            }
            attribute CurrentDimension [0..3] : Profile::DataTypes::MILLIMETER {
                doc /* dimension of material currently in {{term(raw material)}}.*/
            }
            attribute CurrentQuantity [0..1] : Profile::DataTypes::integer {
                doc /* quantity of material currently in {{term(raw material)}}.*/
            }
        }
        part def Material {
            doc /* material used as the {{block(RawMaterial)}}.*/
            attribute id [0..1] : Profile::DataTypes::ID {
                doc /* unique identifier for the material.*/
            }
            attribute name [0..1] : Profile::DataTypes::string {
                doc 
                /* name of the material. 
                 *
                 * Examples: `ULTM9085`, `ABS`, `4140`.*/
            }
            attribute type [1] : Profile::DataTypes::string {
                doc 
                /* type of material. 
                 *
                 * Examples: `Metal`, `Polymer`, `Wood`, `4140`, `Recycled`, `Prestine` and `Used`.*/
            }
            attribute Lot [0..1] : Profile::DataTypes::string {
                doc /* manufacturer's lot code of the material.*/
            }
            attribute Manufacturer [0..1] : Profile::DataTypes::string {
                doc /* name of the material manufacturer.*/
            }
            attribute ManufacturingDate [0..1] : Profile::DataTypes::datetime {
                doc /* manufacturing date of the material from the material manufacturer.*/
            }
            attribute ManufacturingCode [0..1] : Profile::DataTypes::string {
                doc /* lot code of the raw feed stock for the material, from the feed stock manufacturer.*/
            }
            attribute MaterialCode [0..1] : Profile::DataTypes::string {
                doc /* {{term(ASTM)}} standard code that the material complies with.*/
            }
        }
        connection def Material {
            end hasMaterial : Material => target.hasMaterial;
            doc /* See {{sect(Material)}}.*/
            private end : RawMaterial;
        }
        doc 
        /* This section provides semantic information for the {{block(RawMaterial)}} model.
         *
         * ![RawMaterial](figures/RawMaterial.png "RawMaterial"){: width="0.5"}
         *
         * > Note: See {{sect(RawMaterial Schema Diagrams)}} for XML schema.*/
        comment /* Raw Material Asset Information Model*/
        doc 
        /* Raw material represents the source of material for immediate use and sources of material that may or may not be used during the manufacturing process.
         *
         * The {{block(RawMaterial)}} {{block(Asset)}} holds the references to the content stored in the actual {{block(RawMaterial)}} container or derived about the {{block(RawMaterial)}} by the system during operation.*/
    }
    package QIF {
        part def QIFDocument {
            doc /* QIF Document as given by the {{term(QIF)}} standard.*/
        }
        part def QIFDocumentWrapper :> Asset {
            doc /* {{block(Asset)}} that carries the QIF Document.*/
            attribute qifDocumentType [0..1] : Profile::DataTypes::QIFDocumentTypeEnum {
                doc /* contained QIF Document type as defined in the {{term(QIF)}} Standard.*/
            }
            part hasQIFDocument [1] : QIFDocument;
        }
        connection def QIFDocument {
            end hasQIFDocument : QIFDocument => target.hasQIFDocument;
            doc /**/
            private end : QIFDocumentWrapper;
        }
        doc 
        /* This section provides semantic information for the {{block(QIFDocumentWrapper)}} model.
         *
         * ![QIFDocumentWrapper](figures/QIFDocumentWrapper.png "QIFDocumentWrapper"){: width="0.8"}
         *
         * > Note: See {{sect(QIFDocumentWrapper Schema Diagrams)}} for XML schema.*/
        comment /* QIF Asset Information Model*/
        doc 
        /* The {{term(QIF)}} is an American National Standards Institute (ANSI) accredited standard developed by the Digital Metrology Standards Consortium (DMSC) standards development organization. The DMSC is an A-liaison to the International Standards Organization (ISO) Technical Committee (TC) 184. {{term(QIF)}} addresses the needs of the metrology community to have a semantic information model for the exchange of metrology data throughout the verification lifecycle from product design to execution, analysis, and reporting.
         *
         * The MTConnect {{term(QIF)}} {{term(Asset Information Model)}} provides a wrapper around a {{term(QIF)}} document (i.e., a dataset conforming to the QIF Information model) in its native XML representation. The MTConnect standard does not alter or extend the {{term(QIF)}} standard and regards the {{term(QIF)}} standard as a passthrough.
         *
         * Information about the {{term(QIF)}} standards is at the following location: https://qifstandards.org*/
    }
    connection def Configuration {
        end hasConfiguration : 'Device Information Model'::Configurations::Configuration => isConfigurationFor.hasConfiguration;
        doc /* See {{block(Configuration)}} in {{package(Device Information Model)}}.*/
        private end isConfigurationFor : Asset;
    }
    package 'Component Configuration Parameters' {
        part def ComponentConfigurationParameters :> Asset {
            doc /* set of {{block(ParameterSet)}}s that govern the functionality of the related {{block(Component)}}.*/
            part hasParameterSet [1..*] : ParameterSet;
        }
        part def ParameterSet {
            doc /* set of {{block(Parameter)}}s.*/
            attribute name [0..1] : Profile::DataTypes::string {
                doc /* name of the parameter set if more than one exists.*/
            }
            part hasParameter [1..*] : Parameter;
        }
        connection def ParameterSets {
            end hasParameterSet : ParameterSet => target.hasParameterSet;
            doc 
            /* {{block(ParameterSets)}} groups one or more {{block(ParameterSet)}} entities.
             *  See {{sect(ParameterSet)}}.*/
            private end : ComponentConfigurationParameters;
        }
        part def Parameter {
            doc /* property that determines the characteristic or behavior of an entity.*/
            attribute identifier [1] : Profile::DataTypes::string {
                doc /* internal identifier, register, or address.*/
            }
            attribute name [1] : Profile::DataTypes::string {
                doc /* descriptive name.*/
            }
            attribute minimum [0..1] : Profile::DataTypes::double {
                doc /* minimal allowed value.*/
            }
            attribute maximum [0..1] : Profile::DataTypes::double {
                doc /* maximum allowed value.*/
            }
            attribute nominal [0..1] : Profile::DataTypes::double {
                doc /* nominal value.*/
            }
            attribute value [1] : Profile::DataTypes::string {
                doc /* configured value.*/
            }
            attribute units [0..1] : Profile::DataTypes::string {
                doc 
                /* engineering units.
                 *
                 * {{property(Parameter::units)}} **SHOULD** be SI or MTConnect Units.*/
            }
        }
        connection def Parameters {
            end hasParameter : Parameter => target.hasParameter;
            doc 
            /* {{block(Parameters)}} groups one or more {{block(Parameter)}} entities.
             *  See {{sect(Parameter)}}.*/
            private end : ParameterSet;
        }
        doc 
        /* This section provides semantic information for the {{block(ComponentConfigurationParameters)}} model.
         *
         * ![ComponentConfigurationParameters](figures/ComponentConfigurationParameters.png "ComponentConfigurationParameters"){: width="0.8"}
         */
    }
    package Fixture {
        part def Fixture :> PhysicalAsset {
            private attribute FixtureId [0..1] : Profile::DataTypes::ID {
                doc /* identifier of the {{block(Pallet)}}.*/
            }
            private attribute FixtureNumber [0..1] : Profile::DataTypes::integer {
                doc /* number or sequence assigned to the {{block(Fixture)}} in a group of {{block(Fixture)}}s.*/
            }
            private attribute ClampingMethod [0..1] : Profile::DataTypes::string {
                doc /* actuation type of the {{block(Fixture)}}'s clamping mechanism.*/
            }
            private attribute MountingMethod [0..1] : Profile::DataTypes::string {
                doc /* actuation type of the {{block(Fixture)}}'s mounting mechanism.*/
            }
        }
        doc 
        /* This section provides semantic information for the {{block(Fixture)}} model.
         *
         * ![Fixture](figures/Fixture.png "Files"){: width="0.8"}*/
    }
    abstract part def PhysicalAsset :> Asset {
        doc /* abstract physical {{block(Asset)}}.*/
        private attribute ManufactureDate [0..1] : Profile::DataTypes::datetime {
            doc /* date of creation or built of the {{block(Asset)}}.*/
        }
        private attribute CalibrationDate [0..1] : Profile::DataTypes::datetime {
            doc /* date of calibration of the {{block(Asset)}}.*/
        }
        private attribute InspectionDate [0..1] : Profile::DataTypes::datetime {
            doc /* date of last inspection of the {{block(Asset)}}.*/
        }
        private attribute NextInspectionDate [0..1] : Profile::DataTypes::datetime {
            doc /* date of next inspection of the {{block(Asset)}}.*/
        }
        part hasMeasurement [0..*] : Pallet::Measurements::Measurement;
    }
    connection def Measurements {
        end hasMeasurement : Pallet::Measurements::Measurement => target.hasMeasurement;
        private end : PhysicalAsset;
    }
    package Pallet {
        part def Pallet :> PhysicalAsset {
            doc /* {{block(PhysicalAsset)}} that has a portable platform for handling, storing, or moving materials, parts, blanks etc.*/
            private attribute Type [0..1] : Profile::DataTypes::string {
                doc 
                /* type of {{block(Pallet)}}. 
                 *
                 * Common types of pallet include: Process, Warehouse, Shipping, Fixture and Machine.*/
            }
            private attribute PalletId [0..1] : Profile::DataTypes::ID {
                doc /* identifier of the {{block(Pallet)}}.*/
            }
            private attribute PalletNumber [0..1] : Profile::DataTypes::integer {
                doc /* number or sequence assigned to the {{block(Pallet)}} in a group of {{block(Pallet)}}s.*/
            }
            private attribute ClampingMethod [0..1] : Profile::DataTypes::string {
                doc /* actuation type of the {{block(Pallet)}}'s clamping mechanism.*/
            }
            private attribute MountingMethod [0..1] : Profile::DataTypes::string {
                doc /* actuation type of the {{block(Pallet)}}'s mounting mechanism.*/
            }
        }
        package Measurements {
            abstract part def Measurement {
                doc /* constrained scalar value associated with an {{block(Asset)}}*/
                attribute maximum [0..1] : Profile::DataTypes::float {
                    doc /* maximum value for the measurement. */
                }
                attribute minimum [0..1] : Profile::DataTypes::float {
                    doc /* minimum value for the measurement. */
                }
                attribute nativeUnits [0..1] : Profile::DataTypes::NativeUnitEnum {
                    doc /* units the measurement was originally recorded in. See {{package(Device Information Model)}} for the complete list of {{property(DataItem::nativeUnits)}}.*/
                }
                attribute nominal [0..1] : Profile::DataTypes::float {
                    doc /* as advertised value for the measurement.*/
                }
                attribute significantDigits [0..1] : Profile::DataTypes::integer {
                    doc /* number of significant digits in the reported value. */
                }
                attribute units [0..1] : Profile::DataTypes::UnitEnum {
                    doc /* units for the measurements. See {{package(Device Information Model)}} for the complete list of {{property(DataItem::units)}}.*/
                }
                attribute value [0..1] : Profile::DataTypes::float;
            }
            part def Weight :> Measurement {
                doc /* {{termuniversal(weight)}} of the {{block(PhysicalAsset)}}*/
            }
            part def Height :> Measurement {
                doc /* {{termuniversal(height)}} of the {{block(PhysicalAsset)}}*/
            }
            part def Width :> Measurement {
                doc /* {{termuniversal(width)}} of the {{block(PhysicalAsset)}}*/
            }
            part def Length :> Measurement {
                doc /* {{termuniversal(length)}} of the {{block(PhysicalAsset)}}*/
            }
            part def Swing :> Measurement {
                doc /* {{termuniversal(swing)}} of the {{block(PhysicalAsset)}}*/
            }
            part def LoadedWeight :> Measurement {
                doc /* loaded weight of the {{block(PhysicalAsset)}}*/
            }
            part def LoadedHeight :> Measurement {
                doc /* loaded height of the {{block(PhysicalAsset)}}*/
            }
            part def LoadedWidth :> Measurement {
                doc /* loaded width of the {{block(PhysicalAsset)}}*/
            }
            part def LoadedLength :> Measurement {
                doc /* loaded length of the {{block(PhysicalAsset)}}*/
            }
            part def LoadedSwing :> Measurement {
                doc /* loaded swing of the {{block(PhysicalAsset)}}*/
            }
            doc /* This section lists common {{block(Measurement)}} types for a {{block(PhysicalAsset)}}.*/
        }
        doc 
        /* This section provides semantic information for the {{block(Pallet)}} model.
         *
         * ![Pallet](figures/Pallet.png "Files"){: width="0.8"}*/
    }
    package Process {
        part def Process :> Asset {
            doc /* {{block(Asset)}} that is composed of a series of actions to achieve a specific outcome.*/
            private attribute revision [1] : Profile::DataTypes::string {
                doc /* identifier assigned to a process version that reflects a change*/
            }
            part hasRouting [1] : Routing;
            part hasTargets [0..*] : Target::Target;
        }
        connection def ActivityGroups {
            end hasActivityGroup : ActivityGroup => target.hasActivityGroup;
            private end : ProcessStep;
        }
        connection def Targets {
            end hasTarget : Target::TargetRef => target.hasTarget;
            private end : ProcessStep;
        }
        connection def Targets {
            end hasTarget : Target::Target => target.hasTarget;
            private end : ProcessArchetype;
        }
        part def ProcessArchetype :> Asset {
            doc /* {{block(Asset)}} that defines common data for all derived {{block(Process)}}es.*/
            private attribute revision [1] : Profile::DataTypes::string {
                doc /* identifier assigned to a process archetype version that reflects a change*/
            }
            part hasRouting [1..*] : Routing;
            part hasTarget [0..*] : Target::Target;
        }
        connection def {
            end hasActivity : Activity => target.hasActivity;
            private end : ActivityGroup;
        }
        part def Routing {
            doc /* optimal sequence of process steps*/
            private attribute precedence [0..1] : Profile::DataTypes::integer {
                doc /* priority order in which multiple routings are applied or considered for a process*/
            }
            private attribute routingId [1] : Profile::DataTypes::ID {
                doc /* identifier for the routing*/
            }
            part hasProcessStep [1..*] : ProcessStep;
        }
        part def ProcessStep {
            doc /* step involving a flow and/or transformation of material, information, energy, control, or any other element in manufacturing*/
            private attribute stepId [1] : Profile::DataTypes::ID {
                doc /* identifier of the process step*/
            }
            private attribute optional [0..1] : Profile::DataTypes::boolean default false {
                doc /* indicates if a process step is discretionary and not mandatory*/
            }
            private attribute sequence [0..1] : Profile::DataTypes::integer {
                doc /* position of a process step within the progression of process steps to be executed in order*/
            }
            private attribute Description [0..1] : Profile::DataTypes::string {
                doc /* descriptive content for process step*/
            }
            private attribute StartTime [0..1] : Profile::DataTypes::datetime {
                doc /* time when the process step was started*/
            }
            part hasTarget [0..*] : Target::TargetRef;
            part hasActivityGroup [0..*] : ActivityGroup;
            private attribute Duration [0..1] : Profile::DataTypes::float {
                doc /* length of time the process step lasted*/
            }
        }
        part def ActivityGroup {
            doc /* group of {{block(Activity)}}s organized for a common objective within a process step*/
            private attribute activityGroupId [1] : Profile::DataTypes::ID {
                doc /* identifier for the activity group*/
            }
            part hasActivity [1..*] : Activity;
            private attribute name [0..1] : Profile::DataTypes::string {
                doc /* {{termuniversal(name)}} of the activity group*/
            }
        }
        connection def Routings {
            end hasRouting : Routing => target.hasRouting;
            private end : ProcessArchetype;
        }
        connection def {
            end hasProcessStep : ProcessStep => target.hasProcessStep;
            private end : Routing;
        }
        part def Activity {
            doc /* smallest unit of task or action within a process step*/
            private attribute sequence [0..1] : Profile::DataTypes::integer {
                doc /* position of an activity within the progression of activities to be executed in order*/
            }
            private attribute activityId [1] : Profile::DataTypes::ID {
                doc /* identifier for the activity*/
            }
            private attribute precedence [0..1] : Profile::DataTypes::integer {
                doc /* priority order in which an activity should be performed relative to other activities*/
            }
            private attribute optional [0..1] : Profile::DataTypes::boolean default false {
                doc /* indicates if an activity is discretionary and not mandatory*/
            }
            private attribute Description [0..1] : Profile::DataTypes::string {
                doc /* descriptive content for the activity*/
            }
        }
        connection def {
            end hasRouting : Routing => target.hasRouting;
            private end : 'Asset Information Model'::Process::Process;
        }
        connection def Targets {
            end hasTargets : Target::Target => target.hasTargets;
            private end : 'Asset Information Model'::Process::Process;
        }
        package Target {
            abstract part def Target {
                doc 
                /* information related to a {{block(Device)}} or {{block(Component)}} that may implement a {{block(Process)}} or a {{block(Task)}}
                 *
                 */
            }
            part def TargetRef :> Target {
                doc /* reference to an existing {{block(Target)}}*/
                private attribute groupIdRef [1] : Profile::DataTypes::ID {
                    doc /* reference to the identifier provided by a {{block(TargetGroup)}}*/
                }
            }
            part def TargetDevice :> Target {
                doc 
                /* reference to a {{block(Device)}} that is required to implement a {{block(Process)}} or a {{block(Task)}}
                 *
                 */
                private attribute deviceUuid [1] : Profile::DataTypes::UUID {
                    doc /* reference to the {{property(Device::uuid)}}*/
                }
            }
            part def TargetGroup :> Target {
                doc /* reference to a group of {{block(Device)}}s that have the capability to implement a {{block(Process)}} or a {{block(Task)}}*/
                part hasTargetDevice [0..*] : TargetDevice;
                private attribute groupId [1] : Profile::DataTypes::ID {
                    doc /* identifier for a group of {{block(Device)}}s*/
                }
                part hasTargetRef [0..*] : TargetRef;
            }
            connection def {
                end hasTargetDevice : TargetDevice => target.hasTargetDevice;
                private end : TargetGroup;
            }
            part def TargetRequirementTable :> Target {
                doc /* list of requirements a {{block(Device)}} or a {{block(Component)}} **MUST** satisfy to implement a {{block(Process)}} or a {{block(Task)}}*/
                private attribute requirementId [1] : Profile::DataTypes::ID {
                    doc /* identifier for the set of target requirements*/
                }
                part hasEntry [0..*] : 'Observation Information Model'::Representations::Table::Entry;
            }
            connection def {
                end hasEntry : 'Observation Information Model'::Representations::Table::Entry => target.hasEntry;
                private end : TargetRequirementTable;
            }
            connection def {
                end hasTargetRef : TargetRef => target.hasTargetRef;
                private end : TargetGroup;
            }
        }
        doc /* This section provides semantic information for the {{block(Process)}} model.
         */
    }
    package Part {
        abstract part def Identifier {
            doc /* unique name or label for a part.*/
            private attribute type [1] : Profile::DataTypes::PartIdentifierEnum {
                doc /* {{termuniversal(type)}} of identifier*/
            }
            private attribute stepIdRef [0..1] : Profile::DataTypes::ID {
                doc /* reference to the identifier of the process step*/
            }
            private attribute timestamp [1] : Profile::DataTypes::datetime {
                doc /* time when the identifier was reported*/
            }
            private attribute value [1] : Profile::DataTypes::ID;
        }
        part def GroupIdentifier :> Identifier {
            doc /* identifier for a group of parts or a piece of raw material that will be transformed into multiple parts*/
            private attribute type [1] :>> 'Asset Information Model'::Part::Identifier::type : Profile::DataTypes::PartIdentifierEnum default type::GROUP_IDENTIFIER;
        }
        part def PartArchetype :> Asset {
            doc /* {{block(Asset)}} that defines common data for all derived {{block(Part)}}s.*/
            private attribute revision [1] : Profile::DataTypes::string {
                doc /* identifier assigned to a part archetype version that reflects a change*/
            }
            private attribute family [0..1] : Profile::DataTypes::string {
                doc /* identifier for a group of parts that share similar characteristics*/
            }
            private attribute drawing [0..1] : Profile::DataTypes::string {
                doc /* reference to the technical document like a diagram or a blueprint associated with the part archetype*/
            }
            part hasCustomer [0..*] : Customer;
        }
        part def Customer {
            doc /* {{termuniversal(customer)}} for this part*/
            private attribute customerId [0..1] : Profile::DataTypes::ID {
                doc /* identifier for the customer*/
            }
            private attribute name [0..1] : Profile::DataTypes::string {
                doc /* {{termuniversal(name)}} of the customer*/
            }
            private attribute Address [0..1] : Profile::DataTypes::string {
                doc /* {{termuniversal(address)}} of the customer*/
            }
            private attribute Description [0..1] : Profile::DataTypes::string {
                doc /* descriptive content for the customer*/
            }
        }
        connection def Customers {
            end hasCustomer : Customer => target.hasCustomer;
            private end : PartArchetype;
        }
        connection def PartIdentifiers {
            end hasPartIdentifier : Identifier => target.hasPartIdentifier;
            private end : 'Asset Information Model'::Part::Part;
        }
        part def Part :> Asset {
            doc /* {{block(Asset)}} that is a {{term(part)}}.*/
            private attribute family [0..1] : Profile::DataTypes::string {
                doc /* identifier for a group of parts that share similar characteristics*/
            }
            private attribute drawing [0..1] : Profile::DataTypes::string {
                doc /* reference to the technical document like a diagram or a blueprint associated with the part*/
            }
            private attribute revision [1] : Profile::DataTypes::string {
                doc /* identifier assigned to a part version that reflects a change*/
            }
            private attribute nativeId [0..1] : Profile::DataTypes::ID {
                doc /* native identifier for the part*/
            }
            part hasPartIdentifier [0..*] : Identifier;
        }
        part def UniqueIdentifier :> Identifier {
            doc /* unique serialized part identifier.*/
            private attribute type [1] :>> 'Asset Information Model'::Part::Identifier::type : Profile::DataTypes::PartIdentifierEnum default type::UNIQUE_IDENTIFIER;
        }
        doc /* This section provides semantic information for the {{block(Part)}} model.*/
    }
    package Task {
        part def Task :> Asset {
            doc /* {{block(Asset)}} that defines a goal that needs to be achieved*/
            attribute TaskType [1] : Profile::DataTypes::string {
                doc 
                /* semantic goal of the task
                 *
                 * Examples include `MOVE_MATERIAL` and `CHANGE_TOOL`.*/
            }
            attribute TaskState [1] : Profile::DataTypes::TaskStateEnum {
                doc /* {{termuniversal(state)}} of the task*/
            }
            private attribute ParentTaskAssetId [0..1] : Profile::DataTypes::ID {
                doc /* reference to the {{property(Task::assetId)}} of the parent task*/
            }
            part hasSubTask [0..*] : Task::Task;
            ref part hasCoordinator [1] : Collaborator;
            part hasCollaborator [1..*] : Collaborator;
            state def Task {
                item def sucess;
                item def failure;
                item def all_commit;
                item def quorum;
                item def no_commit;
                item def activated;
                item def task_created_by_subtask_coordinator;
                state States {
                    transition first create then INACTIVE;
                    transition first INACTIVE accept activated then PREPARING;
                    transition first PREPARING accept quorum then COMMITTING;
                    transition first COMMITTING accept all_commit then COMMITTED;
                    transition first COMMITTED accept sucess then COMPLETE;
                    transition first COMMITTED accept failure then FAIL;
                    // "Feature Membership -> Transition" is incompatible with textual.
                    // "Feature Membership -> Transition" is incompatible with textual.
                    transition first INACTIVE accept failure then FAIL;
                    transition first COMMITTING accept no_commit then PREPARING;
                    transition first PREPARING accept failure then FAIL;
                    transition first COMMITTING accept failure then FAIL;
                    transition first INACTIVE accept task_created_by_subtask_coordinator then COMMITTING;
                    state create :>> startShot;
                    state INACTIVE;
                    state PREPARING;
                    state COMMITTING;
                    state COMMITTED;
                    state COMPLETE;
                    state FAIL;
                }
            }
        }
        connection def SubTasks {
            end hasSubTask : 'Asset Information Model'::Task::Task => target.hasSubTask;
            doc /* group of {{block(SubTask)}}s*/
            private end : 'Asset Information Model'::Task::Task;
        }
        connection def {
            end hasCoordinator : Collaborator => target.hasCoordinator;
            private end : 'Asset Information Model'::Task::Task;
        }
        connection def Collaborators {
            end hasCollaborator : Collaborator => target.hasCollaborator;
            private end : 'Asset Information Model'::Task::Task;
        }
        package 'Task Archetype' {
            part def Collaborator {
                doc /* {{block(Device)}} or {{block(Component)}} that is required to implement a {{block(Task)}}*/
                attribute collaboratorId [1] : Profile::DataTypes::ID {
                    doc /* identifier for the collaborator*/
                }
                attribute type [0..1] : Profile::DataTypes::string {
                    doc 
                    /* {{termuniversal(type)}} of the collaborator
                     *
                     * Examples include `ROBOT`, `CNC`, `CMM` and `BUFFER`.*/
                }
                attribute optional [0..1] : Profile::DataTypes::boolean default false {
                    doc /* indicates if the collaborator is discretionary and not mandatory to implement a task*/
                }
                part hasTarget [1..*] : Process::Target::Target;
                state def Collaborator {
                    item def task_created;
                    item def commit_failure;
                    item def commit;
                    item def success;
                    item def failure;
                    item def task_created_by_subtask_coordinator;
                    state States {
                        transition first unavailable then INACTIVE;
                        transition first INACTIVE accept task_created then PREPARING;
                        transition first PREPARING accept commit then COMMITTED;
                        transition first COMMITTED accept commit_failure then PREPARING;
                        transition first COMMITTED accept success then INACTIVE;
                        transition first COMMITTED accept failure then INACTIVE;
                        transition first INACTIVE accept task_created_by_subtask_coordinator then COMMITTED;
                        state unavailable :>> startShot;
                        state INACTIVE;
                        state PREPARING;
                        state COMMITTED;
                    }
                }
                state def Coordinator {
                    item def create_and_bind_to_task;
                    item def success;
                    item def failure;
                    state States {
                        transition first unavailable then INACTIVE;
                        transition first INACTIVE accept create_and_bind_to_task then COMMITTED;
                        transition first COMMITTED accept success then INACTIVE;
                        transition first COMMITTED accept failure then INACTIVE;
                        state unavailable :>> startShot;
                        state INACTIVE;
                        state COMMITTED;
                    }
                }
                exhibit state : Collaborator;
            }
            connection def Targets {
                end hasTarget : Process::Target::Target => target.hasTarget;
                private end : Collaborator;
            }
            part def TaskArchetype :> Asset {
                doc /* {{block(Asset)}} that defines common data for all derived {{block(Task)}}s*/
                ref part hasCollaborator [1..*] : Collaborator;
                ref part hasCoordinator [1] : Collaborator;
                attribute TaskType [1] : Profile::DataTypes::string {
                    doc 
                    /* semantic goal of the task
                     *
                     * Examples include `MOVE_MATERIAL` and `CHANGE_TOOL`.*/
                }
                ref part isSubTaskOf [0..1] : TaskArchetype;
                part hasSubTask [0..*] : TaskArchetype;
                private attribute Priority [0..1] : Profile::DataTypes::integer {
                    doc /* relative importance that determines the order in which a task should be performed*/
                }
                part hasTarget [0..*] : Process::Target::Target;
            }
            connection def SubTaskRef {
                end taskArchetype2 : TaskArchetype => taskArchetype3.isSubTaskOf;
                end taskArchetype3 : TaskArchetype => taskArchetype2.hasSubTask;
                attribute 'parallel' [0..1] : Profile::DataTypes::boolean default false {
                    doc /* indication signifying that subtasks can be executed simultaneously*/
                }
                attribute group [0..1] : Profile::DataTypes::string {
                    doc /* identifier to a set of subtasks organized to be treated collectively within the parent task*/
                }
                attribute order [1] : Profile::DataTypes::integer {
                    doc /* position of a subtask within an explicit arrangement where one subtask follows another*/
                }
                attribute optional [0..1] : Profile::DataTypes::boolean default false {
                    doc /* indicates if a subtask is discretionary and not mandatory*/
                }
                private attribute value [0..1] : Profile::DataTypes::string;
            }
            connection def Coordinator {
                end hasCoordinator : Collaborator => target.hasCoordinator;
                private end : TaskArchetype;
            }
            connection def Targets {
                end hasTarget : Process::Target::Target => target.hasTarget;
                private end : TaskArchetype;
            }
            connection def Collaborators {
                end hasCollaborator : Collaborator => target.hasCollaborator;
                private end : TaskArchetype;
            }
            doc /* This section provides semantic information for the {{block(TaskArchetype)}} model.
             */
        }
        part def Collaborator {
            doc /* {{block(Device)}} or {{block(Component)}} that is required to implement a {{block(Task)}}*/
            attribute collaboratorId [1] : Profile::DataTypes::ID {
                doc /* identifier for the collaborator*/
            }
            attribute type [0..1] : Profile::DataTypes::string {
                doc 
                /* {{termuniversal(type)}} of the collaborator
                 *
                 * Examples include `ROBOT`, `CNC`, `CMM` and `BUFFER`.*/
            }
            private attribute collaboratorDeviceUuid [1] : Profile::DataTypes::ID {
                doc /* reference to the {{block(Device::uuid)}} of the collaborating device*/
            }
            private attribute requirementId [0..1] : Profile::DataTypes::ID {
                doc /* reference to the identifier of the target requirements that the collaborator satisfies*/
            }
            state def Collaborator {
                item def task_created;
                item def commit_failure;
                item def commit;
                item def success;
                item def failure;
                item def task_created_by_subtask_coordinator;
                state States {
                    transition first unavailable then INACTIVE;
                    transition first INACTIVE accept task_created then PREPARING;
                    transition first PREPARING accept commit then COMMITTED;
                    transition first COMMITTED accept commit_failure then PREPARING;
                    transition first COMMITTED accept success then INACTIVE;
                    transition first COMMITTED accept failure then INACTIVE;
                    transition first INACTIVE accept task_created_by_subtask_coordinator then COMMITTED;
                    state unavailable :>> startShot;
                    state INACTIVE;
                    state PREPARING;
                    state COMMITTED;
                }
            }
            state def Coordinator {
                item def create_and_bind_to_task;
                item def success;
                item def failure;
                state States {
                    transition first unavailable then INACTIVE;
                    transition first INACTIVE accept create_and_bind_to_task then COMMITTED;
                    transition first COMMITTED accept success then INACTIVE;
                    transition first COMMITTED accept failure then INACTIVE;
                    state unavailable :>> startShot;
                    state INACTIVE;
                    state COMMITTED;
                }
            }
            exhibit state : Collaborator;
        }
        doc /* This section provides semantic information for the {{block(Task)}} model.
         */
    }
    doc 
    /* The MTConnect Standard supports a simple distributed storage mechanism that allows applications and equipment to share and exchange complex information models in a similar way to a distributed data store.  The {{term(Asset Information Model)}} associates each {{block(MTConnectAssets)}} entity with a unique identifier and allows for some predefined mechanisms to find, create, request, update, and delete these electronic documents in a way that provides for consistency across multiple pieces of equipment.
     *
     * The protocol provides a limited mechanism of accessing {{termplural(Asset)}} using the following properties: {{property(Asset::assetId)}}, {{term(asset)}} type (element name of {{term(asset)}} root), and the piece of equipment associated with the {{term(asset)}}.  These access strategies will provide the following services and answer the following questions: What {{termplural(asset)}} are from a particular piece of equipment?  What are the {{termplural(asset)}} of a particular type? What {{term(asset)}} is stored for a given {{property(Asset::assetId)}}?
     *
     * Although these mechanisms are provided, an {{term(agent)}} should not be considered a data store or a system of reference.  The {{term(agent)}} is providing an ephemeral storage capability that will temporarily manage the data for applications wishing to communicate and manage data as needed by the various processes.  An application cannot rely on an {{term(agent)}} for long term persistence or durability since the {{term(agent)}} is only required to temporarily store the {{term(asset)}} data and may require another system to provide the source data upon initialization.  An {{term(agent)}} is always providing the best-known equipment centric view of the data given the limitations of that piece of equipment.
     *
     * The MTConnect Standard has two data item types to support change notification when an {{term(Asset)}} is added, updated or removed. {{block(AssetChanged)}} states the {{property(Asset::assetId)}} of the {{term(Asset)}} that has been added or updated. {{block(AssetRemoved)}} states the {{property(Asset::assetId)}} of the {{term(Asset)}} that has been removed. See {{package(Observation Information Model)}} for more details.*/
    comment /* Assets Appendix*/
    doc 
    /* {{newpage()}}
     *
     * ## XML Schema Diagrams
     *
     * See XML schemas for the MTConnect standard here: {{url(https://schemas.mtconnect.org/)}}.
     *
     * ### Assets Schema Diagrams
     *
     * See `Asset` element in `MTConnectAssets` schema.
     *
     * See `Description` element in `MTConnectAssets` schema.
     *
     * ### CuttingTool Schema Diagrams
     *
     * See `CuttingTool` element in `MTConnectAssets` schema.
     *
     * See `CuttingToolDefinition` element in `MTConnectAssets` schema.
     *
     * See `CuttingToolArchetypeReference` element in `MTConnectAssets` schema.
     *
     * ### CuttingToolLifeCycle Schema Diagrams
     *
     * See `CuttingToolLifeCycle` element in `MTConnectAssets` schema.
     *
     * See `CutterStatus` element in `MTConnectAssets` schema.
     *
     * See `Location` element in `MTConnectAssets` schema.
     *
     * See `Measurement` element in `MTConnectAssets` schema.
     *
     * See `ProcessFeedRate` element in `MTConnectAssets` schema.
     *
     * See `ProcessSpindleSpeed` element in `MTConnectAssets` schema.
     *
     * See `ReconditionCount` element in `MTConnectAssets` schema.
     *
     * See `ToolLife` element in `MTConnectAssets` schema.
     *
     * ### CuttingItem Schema Diagrams
     *
     * See `CuttingItems` element in `MTConnectAssets` schema.
     *
     * See `CuttingItem` element in `MTConnectAssets` schema.
     *
     * See `ItemLife` element in `MTConnectAssets` schema.
     *
     * ### ISO 13399 Diagrams
     *
     * #### Measurement Diagrams
     *
     * ![Cutting Tool Measurement 3](figures/Cutting%20Tool%20Measurement%203.png "Cutting Tool Measurement 3"){: width="0.8"}
     *
     * ![Cutting Tool Measurement 4](figures/Cutting%20Tool%20Measurement%204.png "Cutting Tool Measurement 4"){: width="0.8"}
     *
     * ![Cutting Tool Measurement 5](figures/Cutting%20Tool%20Measurement%205.png "Cutting Tool Measurement 5"){: width="0.8"}
     *
     * ![Cutting Tool Measurement 6](figures/Cutting%20Tool%20Measurement%206.png "Cutting Tool Measurement 6"){: width="0.8"}
     *
     * ![Cutting Tool Measurement 7](figures/Cutting%20Tool%20Measurement%207.png "Cutting Tool Measurement 7"){: width="0.8"}
     *
     * ![Cutting Tool Measurement 8](figures/Cutting%20Tool%20Measurement%208.png "Cutting Tool Measurement 8"){: width="0.8"}
     *
     * ### Cutting Tool Examples
     *
     * #### Shell Mill
     *
     * ![Shell Mill Side View](figures/Shell%20Mill%20Side%20View.png "Shell Mill Side View"){: width="0.8"}
     *
     * ![Indexable Insert Measurements](figures/Indexable%20Insert%20Measurements.png "Indexable Insert Measurements"){: width="0.8"}
     *
     * ~~~~xml
     * <?xml version="1.0" encoding="UTF-8"?>
     * <MTConnectAssets 
     * xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2
     * http://mtconnect.org/schemas/MTConnectAssets\_1.2.xsd">
     *   <Header creationTime="2011-05-11T13:55:22" 
     *   assetBufferSize="1024" sender="localhost"
     *   assetCount="2" version="1.2" instanceId="1234"/>
     *   <Assets>
     *   <CuttingTool serialNumber="1" toolId="KSSP300R4SD43L240" 
     *   timestamp="2011-05-11T13:55:22" assetId="KSSP300R4SD43L240.1" 
     *   manufacturers="KMT,Parlec">
     *     <CuttingToolLifeCycle>
     *     <CutterStatus><Status>NEW</Status></CutterStatus>
     *     <ProcessSpindleSpeed maximum="13300" 
     *     nominal="605">10000</ProcessSpindleSpeed>
     *     <ProcessFeedRate
     *     nominal="9.22">9.22</ProcessSpindleSpeed>
     *     <ConnectionCodeMachineSide>CV50
     *     </ConnectionCodeMachineSide>
     *     <Measurements>
     *       <BodyDiameterMax code="BDX">73.25
     *       </BodyDiameterMax>
     *       <OverallToolLength nominal="222.25" 
     *         minimum="221.996" maximum="222.504" 
     *         code="OAL">222.25</OverallToolLength>
     *       <UsableLengthMax code="LUX" nominal="82.55">82.55
     *       </UsableLengthMax>
     *       <CuttingDiameterMax code="DC" nominal="76.2" 
     *         maximum="76.213" minimum="76.187">76.2
     *       </CuttingDiameterMax>
     *       <BodyLengthMax code="LF" nominal="120.65" 
     *         maximum="120.904" minimum="120.404">120.65
     *       </BodyLengthMax>
     *       <DepthOfCutMax code="APMX" 
     *       nominal="60.96">60.95</DepthOfCutMax>
     *       <FlangeDiameterMax code="DF" 
     *         nominal="98.425">98.425</FlangeDiameterMax>
     *     </Measurements>
     *     <CuttingItems count="24">
     *       <CuttingItem indices="1-24" itemId="SDET43PDER8GB" 
     *         manufacturers="KMT" grade="KC725M">
     *         <Measurements>
     *           <CuttingEdgeLength code="L" nominal="12.7" 
     *             minimum="12.675" maximum="12.725">12.7
     *           </CuttingEdgeLength>
     *         <WiperEdgeLength code="BS" nominal=
     *           "2.56">2.56</WiperEdgeLength>
     *         <IncribedCircleDiameter code="IC"
     *           nominal="12.7">12.7
     *         </IncribedCircleDiameter>
     *         <CornerRadius code="RE" nominal="0.8">
     *           0.8</CornerRadius>
     *       </Measurements>
     *       </CuttingItem>
     *     </CuttingItems>
     *     </CuttingToolLifeCycle>
     *     </CuttingTool>
     *   </Assets>
     * </MTConnectAssets>
     * ~~~~
     * {: caption="Example for Indexable Insert Measurements"}
     *
     * {{pagebreak()}}
     *
     * #### Step Drill
     *
     * ![Step Mill Side View](figures/Step%20Mill%20Side%20View.png "Step Mill Side View"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-
     *   11T13:55:22" assetBufferSize="1024" 
     *   sender="localhost" assetCount="2" version="1.2" instanceId="1234"/>
     *   <Assets>
     *     <CuttingTool serialNumber="1 " toolId="B732A08500HP" 
     *     timestamp="2011-05-11T13:55:22" assetId="B732A08500HP " 
     *     manufacturers="KMT,Parlec">
     *       <Description>
     *         Step Drill - KMT, B732A08500HP Grade KC7315
     *         Adapter - Parlec, C50-M12SF300-6
     *       </Description>
     *       <CuttingToolLifeCycle>
     *         <CutterStatus><Status>NEW</Status></CutterStatus>
     *         <ProcessSpindleSpeed nominal="5893">5893</ProcessSpindleSpeed>
     *         <ProcessFeedRate nominal="2.5">2.5</ProcessFeedRate>
     *         <ConnectionCodeMachineSide>CV50 Taper</ConnectionCodeMachineSide>
     *         <Measurements>
     *           <BodyDiameterMax code="BDX">31.8</BodyDiameterMax>
     *           <BodyLengthMax code="LBX" nominal="120.825" maximum="126.325" 
     *           minimum="115.325">120.825</BodyLengthMax>
     *           <ProtrudingLength code="LPR" nominal="155.75" maximum="161.25" 
     *           minimum="150.26">155.75</ProtrudingLength>
     *           <FlangeDiameterMax code="DF" 
     *           nominal="98.425">98.425</FlangeDiameterMax>
     *           <OverallToolLength nominal="257.35" minimum="251.85" 
     *           maximum="262.85" code="OAL">257.35</OverallToolLength>
     *         </Measurements>
     *         <CuttingItems count="2">
     *           <CuttingItem indices="1" manufacturers="KMT" grade="KC7315">>
     *             <Measurements>
     *               <CuttingDiameter code="DC1" nominal="8.5" maximum="8.521" 
     *               minimum="8.506">8.5135</CuttingDiameter>
     *               <StepIncludedAngle code="STA1" nominal="90" maximum="91" 
     *               minimum="89">90</StepIncludedAngle>
     *               <FunctionalLength code="LF1" nominal="154.286" 
     *               minimum="148.786" 
     *               maximum="159.786">154.286</FunctionalLength>
     *               <StepDiameterLength code="SDL1" 
     *               nominal="9">9</StepDiameterLength>
     *               <PointAngle code="SIG" nominal="135" minimum="133" 
     *               maximum="137">135</PointAngle>
     *             </Measurements>
     *           </CuttingItem>
     *           <CuttingItem indices="2" manufacturers="KMT" grade="KC7315">>
     *             <Measurements>
     *               <CuttingDiameter code="DC2" nominal="12" maximum="12.011" 
     *               minimum="12">12</CuttingDiameter>
     *               <FunctionalLength code="LF2" nominal="122.493" 
     *               maximum="127.993" 
     *               minimum="116.993">122.493</FunctionalLength>
     *               <StepDiameterLength code="SDL2" 
     *               nominal="9">9</StepDiameterLength>
     *             </Measurements>
     *           </CuttingItem>
     *         </CuttingItems>
     *       </CuttingToolLifeCycle>
     *     </CuttingTool>
     *   </Assets>
     * </MTConnectAssets>
     * ~~~~
     * {: caption="Example for Step Mill Side View"}
     *
     * {{pagebreak()}}
     *
     * #### Shell Mill with Individual Loci
     *
     * ![Shell Mill with Explicate Loci](figures/Shell%20Mill%20with%20Explicate%20Loci.png "Shell Mill with Explicate Loci"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="KSSP300R4SD43L240" 
     *     timestamp="2011-05-11T13:55:22" assetId="KSSP300R4SD43L240.1" 
     *     manufacturers="KMT,Parlec">
     *       <Description>Keyway: 55 degrees</Description>
     *       <CuttingToolLifeCycle>
     *         <CutterStatus><Status>NEW</Status></CutterStatus>
     *         <Measurements>
     *           <UsableLengthMax code="LUX" 
     *           nominal="82.55">82.55</UsableLengthMax>
     *           <CuttingDiameterMax code="DC" nominal="76.2" maximum="76.213" 
     *           minimum="76.187">76.2</CuttingDiameterMax>
     *           <DepthOfCutMax code="APMX" nominal="60.96">60.95</DepthOfCutMax>
     *         </Measurements>
     *         <CuttingItems count="24">
     *           <CuttingItem indices="1" itemId="SDET43PDER8GB" 
     *           manufacturers="KMT">
     *             <Locus>FLUTE: 1, ROW: 1</Locus>
     *             <Measurements>
     *              <DriveAngle code="DRVA" nominal="55">55</DriveAngle>
     *            </Measurements>
     *           </CuttingItem>
     *           <CuttingItem indices="2-24" itemId="SDET43PDER8GB" 
     *           manufacturers="KMT">
     *             <Locus>FLUTE: 2-4, ROW: 1; FLUTE: 1-4, ROW 2-6</Locus>
     *           </CuttingItem>
     *         </CuttingItems>
     *       </CuttingToolLifeCycle>
     *     </CuttingTool>
     *   </Assets>
     * </MTConnectAssets>
     * ~~~~
     * {: caption="Example for Shell Mill with Explicate Loci"}
     *
     * {{pagebreak()}}
     *
     * #### Drill with Individual Loci
     *
     * ![Step Drill with Explicate Loci](figures/Step%20Drill%20with%20Explicate%20Loci.png "Step Drill with Explicate Loci"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="KSEM0781LD" 
     *     timestamp="2011-05-11T13:55:22" assetId="KSEM0781LD.1" manufacturers="KMT">
     *       <CuttingToolLifeCycle>
     *         <CutterStatus><Status>NEW</Status></CutterStatus>
     *         <ConnectionCodeMachineSide>HSK63A</ConnectionCodeMachineSide>
     *         <Measurements>
     *           <BodyDiameterMax code="BDX">52.75</BodyDiameterMax>
     *           <OverallToolLength nominal="172.29" 
     *           code="OAL">172.29</OverallToolLength>
     *           <UsableLengthMax code="LUX" nominal="49">49</UsableLengthMax>
     *           <FlangeDiameterMax code="DF" 
     *           nominal="62.94">62.94</FlangeDiameterMax>
     *         </Measurements>
     *         <CuttingItems count="3">
     *           <CuttingItem indices="1" itemId="KSEM0781LD" manufacturers="KMT" 
     *           grade="KC7015">
     *             <Locus>FLUTE: 1, ROW: 1</Locus>
     *             <Measurements>
     *          <FunctionalLength code="LF1" nominal="154.42">154.42</FunctionalLength>
     *          <CuttingDiameter code="DC1" nominal="19.844">19.844</CuttingDiameter>
     *          <PointAngle code="SIG" nominal="140">140</PointAngle>
     *          <ToolCuttingEdgeAngle code="KAPR1" nominal="45">45</ToolCuttingEdgeAngle>
     *          <StepDiameterLength code="SLD1" nominal="39.8">39.8</StepDiameterLength>
     *             </Measurements>
     *           </CuttingItem>
     *           <CuttingItem indices="2-3" itemId="TPMT-21.52-FP" 
     *           manufacturers="KMT" grade="KCM15">
     *             <Locus>FLUTE: 1-2, ROW: 2</Locus>
     *             <Measurements>
     *          <FunctionalLength code="LF2" nominal="112.9">119.2</FunctionalLength>
     *          <CuttingDiameter code="DC2" nominal="31">31</CuttingDiameter>
     *             </Measurements>
     *           </CuttingItem>
     *         </CuttingItems>
     *       </CuttingToolLifeCycle>
     *     </CuttingTool>
     *   </Assets>
     * </MTConnectAssets>
     * ~~~~
     * {: caption="Example for Step Drill with Explicate Loci"}
     *
     * {{pagebreak()}}
     *
     * #### Shell Mill with Different Inserts on First Row
     *
     * ![Shell Mill with Different Inserts on First Row](figures/Shell%20Mill%20with%20Different%20Inserts%20on%20First%20Row.png "Shell Mill with Different Inserts on First Row"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="XXX" timestamp="2011-05-11T13:55:22" 
     *     assetId="XXX.1" manufacturers="KMT">
     *       <CuttingToolLifeCycle>
     *         <CutterStatus><Status>NEW</Status></CutterStatus>
     *         <Measurements>
     *           <DepthOfCutMax code="APMX" nominal="47.8">47.8</DepthOfCutMax>
     *           <CuttingDiameterMax code="DC" 
     *           nominal="50.8">50.8</CuttingDiameterMax>
     *           <UsableLengthMax code="LUX" 
     *           nominal="78.74">78.74</UsableLengthMax>
     *         </Measurements>
     *         <CuttingItems count="9">
     *           <CuttingItem indices="1-3" itemId="EDPT180564PDER-LD" 
     *           manufacturers="KMT">
     *             <Locus>FLUTE: 1-3, ROW: 1</Locus>
     *             <Measurements>
     *               <CornerRadius code="RE" nominal="6.25">6.35</CornerRadius>
     *             </Measurements>
     *           </CuttingItem>
     *           <CuttingItem indices="4-9" itemId="EDPT180508PDER-LD" 
     *           manufacturers="KMT">
     *             <Locus>FLANGE: 1-4, ROW: 2-3</Locus>
     *           </CuttingItem>
     *         </CuttingItems>
     *       </CuttingToolLifeCycle>
     *     </CuttingTool>
     *   </Assets>
     * </MTConnectAssets>
     * ~~~~
     * {: caption="Example for Shell Mill with Different Inserts on First Row"}
     *
     * ### File Schema Diagrams
     *
     * See `File` element in `MTConnectAssets` schema.
     *
     * ### RawMaterial Schema Diagrams
     *
     * See `RawMaterial` element in `MTConnectAssets` schema.
     *
     * ### QIFDocumentWrapper Schema Diagrams
     *
     * See `QIFDocumentWrapper` element in `MTConnectAssets` schema.*/
}
package Fundamentals {
    package 'MTConnect Protocol' {
        package 'MTConnectAssets Response Document' {
            part def MTConnectAssets {
                doc 
                /* root entity of an {{term(MTConnectAssets Response Document)}} that contains the {{term(Asset Information Model)}} of {{block(Asset)}} types.
                 *
                 * ![MTConnectAssets](figures/MTConnectAssets.png "MTConnectAssets"){: width="0.8"}
                 *
                 * > Note: Additional properties of {{block(MTConnectAssets)}} **MAY** be defined for schema and namespace declaration. See {{sect(Schema and Namespace Declaration Information)}} for an {{term(XML)}} example.*/
                ref part hasHeader [1] : Fundamentals::'MTConnect Protocol'::'MTConnectAssets Response Document'::Header;
                part hasAsset [0..*] : 'Asset Information Model'::Asset;
            }
            connection def Header {
                end hasHeader : Fundamentals::'MTConnect Protocol'::'MTConnectAssets Response Document'::Header => target.hasHeader;
                end : MTConnectAssets;
            }
            part def Header {
                doc /* provides information from an {{term(agent)}} defining version information, storage capacity, and parameters associated with the data management within the {{term(agent)}}.*/
                attribute deviceModelChangeTime [1] : Profile::DataTypes::datetime {
                    doc /* timestamp of the last update of the {{block(Device)}} information for any device.*/
                }
                attribute assetBufferSize [1] : Profile::DataTypes::uint32 {
                    doc 
                    /* maximum number of {{block(Asset)}} types that can be stored in the {{term(agent)}} that published the {{term(response document)}}.  
                     *
                     * > Note: The implementer is responsible for allocating the appropriate amount of storage capacity required to accommodate the {{property(Header::assetBufferSize)}}.
                     */
                }
                attribute assetCount [1] : Profile::DataTypes::uint32 {
                    doc 
                    /* current number of {{block(Asset)}} that are currently stored in the {{term(agent)}} as of the {{property(Header::creationTime)}} that the {{term(agent)}} published the {{term(response document)}}.
                     *
                     * {{property(Header::assetCount)}} **MUST NOT** be larger than the value reported for {{property(Header::assetBufferSize)}}.
                     */
                }
                attribute creationTime [1] : Profile::DataTypes::datetime {
                    doc /* timestamp that an {{term(agent)}} published the {{term(response document)}}. */
                }
                attribute instanceId [1] : Profile::DataTypes::uint64 {
                    doc 
                    /* identifier for a specific instantiation of the {{term(buffer)}} associated with the {{term(agent)}} that published the {{term(response document)}}.  
                     *      
                     * {{property(Header::instanceId)}} **MUST** be changed to a different unique number each time the {{term(buffer)}} is cleared and a new set of data begins to be collected.*/
                }
                attribute sender [1] : Profile::DataTypes::string {
                    doc 
                    /* identification defining where the {{term(agent)}} that published the {{term(response document)}} is installed or hosted.
                     *
                     * {{property(Header::sender)}} **MUST** be either an IP Address or Hostname describing where the {{term(agent)}} is installed or the URL of the {{term(agent)}}; e.g., `http://<address>[:port]/`. 
                     *
                     * > Note:  The port number need not be specified if it is the default HTTP port 80.*/
                }
                attribute testIndicator [0..1] : Profile::DataTypes::boolean default false {
                    doc 
                    /* indicates whether the {{term(agent)}} that published the {{term(response document)}} is operating in a test mode.
                     *
                     * If {{property(Header::testIndicator)}} is not specified, the value for {{property(Header::testIndicator)}} **MUST** be interpreted to be `false`.*/
                }
                attribute version [1] : Profile::DataTypes::version {
                    doc 
                    /* {{term(major)}}, {{term(minor)}}, and {{term(revision)}} number of the MTConnect Standard that defines the {{term(semantic data model)}} that represents the content of the {{term(response document)}}. It also includes the revision number of the {{term(schema)}} associated with that specific {{term(semantic data model)}}.
                     *
                     * As an example, the value reported for {{property(Header::version)}} for a {{term(response document)}} that was structured based on {{term(schema)}} revision 10 associated with Version 1.4.0 of the MTConnect Standard would be:  1.4.0.10*/
                }
                private attribute validation [0..1] : Profile::DataTypes::boolean default false {
                    doc /* indicates if the {{term(MTConnect Agent)}} is validating against the normative model.*/
                }
            }
            doc /* This section provides semantic information for the {{block(MTConnectAssets)}} entity.*/
        }
        package 'MTConnectDevices Response Document' {
            part def MTConnectDevices {
                doc 
                /* root entity of an {{term(MTConnectDevices Response Document)}} that contains the {{term(Device Information Model)}} of one or more {{block(Device)}} entities.
                 *
                 * ![MTConnectDevices](figures/MTConnectDevices.png "MTConnectDevices"){: width="0.8"}
                 *
                 * > Note: Additional properties of {{block(MTConnectDevices)}} **MAY** be defined for schema and namespace declaration. See {{sect(Schema and Namespace Declaration Information)}} for an {{term(XML)}} example.*/
                part hasHeader [1] : Fundamentals::'MTConnect Protocol'::'MTConnectDevices Response Document'::Header;
                part hasDevice [1..*] : 'Device Information Model'::Device;
            }
            connection def Devices {
                end hasDevice : 'Device Information Model'::Device => target.hasDevice;
                doc /* {{block(Devices)}} groups one or more {{block(Device)}} entities. See {{package(Device Information Model)}} for more detail.*/
                private end : MTConnectDevices;
            }
            connection def AssetCounts {
                end hasAssetCount : AssetCount => target.hasAssetCount;
                doc /* {{block(AssetCounts)}} groups {{block(AssetCount)}} entities.*/
                private end : Fundamentals::'MTConnect Protocol'::'MTConnectDevices Response Document'::Header;
            }
            connection def Header {
                end hasHeader : Fundamentals::'MTConnect Protocol'::'MTConnectDevices Response Document'::Header => target.hasHeader;
                private end : MTConnectDevices;
            }
            part def Header {
                doc /* provides information from an {{term(agent)}} defining version information, storage capacity, and parameters associated with the data management within the {{term(agent)}}.*/
                attribute assetBufferSize [1] : Profile::DataTypes::uint32 {
                    doc 
                    /* maximum number of {{block(Asset)}} types that can be stored in the {{term(agent)}} that published the {{term(response document)}}.  
                     *
                     * > Note: The implementer is responsible for allocating the appropriate amount of storage capacity required to accommodate the {{property(Header::assetBufferSize)}}.
                     */
                }
                attribute assetCount [1] : Profile::DataTypes::uint32 {
                    doc 
                    /* current number of {{block(Asset)}} that are currently stored in the {{term(agent)}} as of the {{property(Header::creationTime)}} that the {{term(agent)}} published the {{term(response document)}}.
                     *
                     * {{property(Header::assetCount)}} **MUST NOT** be larger than the value reported for {{property(Header::assetBufferSize)}}.
                     */
                }
                attribute bufferSize [1] : Profile::DataTypes::uint32 {
                    doc 
                    /* maximum number of {{termplural(DataItem)}} that **MAY** be retained in the {{term(agent)}} that published the {{term(response document)}} at any point in time.
                     *
                     * > Note 1 to entry:  {{property(Header::bufferSize)}} represents the maximum number of sequence numbers that **MAY** be stored in the {{term(agent)}}. 
                     *
                     * > Note 2 to entry: The implementer is responsible for allocating the appropriate amount of storage capacity required to accommodate the {{property(Header::bufferSize)}}.
                     */
                }
                attribute creationTime [1] : Profile::DataTypes::datetime {
                    doc /* timestamp that an {{term(agent)}} published the {{term(response document)}}. */
                }
                attribute instanceId [1] : Profile::DataTypes::uint64 {
                    doc 
                    /* identifier for a specific instantiation of the {{term(buffer)}} associated with the {{term(agent)}} that published the {{term(response document)}}.  
                     *      
                     * {{property(Header::instanceId)}} **MUST** be changed to a different unique number each time the {{term(buffer)}} is cleared and a new set of data begins to be collected.*/
                }
                attribute sender [1] : Profile::DataTypes::string {
                    doc 
                    /* identification defining where the {{term(agent)}} that published the {{term(response document)}} is installed or hosted.
                     *
                     * {{property(Header::sender)}} **MUST** be either an IP Address or Hostname describing where the {{term(agent)}} is installed or the URL of the {{term(agent)}}; e.g., `http://<address>[:port]/`. 
                     *
                     * > Note:  The port number need not be specified if it is the default HTTP port 80.*/
                }
                attribute testIndicator [0..1] : Profile::DataTypes::boolean default false {
                    doc 
                    /* indicates whether the {{term(agent)}} that published the {{term(response document)}} is operating in a test mode.
                     *
                     * If {{property(Header::testIndicator)}} is not specified, the value for {{property(Header::testIndicator)}} **MUST** be interpreted to be `false`.*/
                }
                attribute version [1] : Profile::DataTypes::version {
                    doc 
                    /* {{term(major)}}, {{term(minor)}}, and {{term(revision)}} number of the MTConnect Standard that defines the {{term(semantic data model)}} that represents the content of the {{term(response document)}}. It also includes the revision number of the {{term(schema)}} associated with that specific {{term(semantic data model)}}.
                     *
                     * As an example, the value reported for {{property(Header::version)}} for a {{term(response document)}} that was structured based on {{term(schema)}} revision 10 associated with Version 1.4.0 of the MTConnect Standard would be:  1.4.0.10*/
                }
                attribute firstSequence [0..1] : Profile::DataTypes::uint64 {
                    doc /* {{term(sequence number)}} assigned to the oldest piece of {{term(streaming data)}} stored in the {{term(buffer)}} of the {{term(agent)}} immediately prior to the time that the {{term(agent)}} published the {{term(response document)}}.   */
                }
                attribute lastSequence [0..1] : Profile::DataTypes::uint64 {
                    doc 
                    /* {{term(sequence number)}} assigned to the last piece of {{term(streaming data)}} that was added to the {{term(buffer)}} of the {{term(agent)}} immediately prior to the time that the {{term(agent)}} published the {{term(response document)}}.   
                     *
                     */
                }
                attribute nextSequence [0..1] : Profile::DataTypes::uint64 {
                    doc 
                    /* {{term(sequence number)}} of the piece of {{term(streaming data)}} that is the next piece of data to be retrieved from the {{term(buffer)}} of the {{term(agent)}} that was not included in the {{term(response document)}} published by the {{term(agent)}}.
                     *
                     * If the {{term(streaming data)}} included in the {{term(response document)}} includes the last piece of data stored in the {{term(buffer)}} of the {{term(agent)}} at the time that the document was published, then the value reported for {{property(Header::nextSequence)}} **MUST** be equal to {{property(Header::lastSequence)}} + 1.*/
                }
                attribute deviceModelChangeTime [1] : Profile::DataTypes::datetime {
                    doc /* timestamp of the last update of the {{block(Device)}} information for any device.*/
                }
                part hasAssetCount [0..*] : AssetCount;
                private attribute validation [0..1] : Profile::DataTypes::boolean default false {
                    doc /* indicates if the {{term(MTConnect Agent)}} is validating against the normative model.*/
                }
            }
            part def AssetCount {
                doc /* count of each asset type currently in the {{term(agent)}}.*/
                attribute assetType [1] : Profile::DataTypes::string {
                    doc /* type of {{term(Asset)}}.*/
                }
            }
            doc /* This section provides semantic information for the {{block(MTConnectDevices)}} entity.*/
        }
        package 'MTConnectStreams Response Document' {
            connection def Streams {
                end hasDeviceStream : 'Observation Information Model'::DeviceStream => target.hasDeviceStream;
                doc /* {{block(Streams)}} groups one or more {{block(DeviceStream)}} entities. See {{package(Observation Information Model)}} for more detail.*/
                end : MTConnectStreams;
            }
            connection def Header {
                end hasHeader : Fundamentals::'MTConnect Protocol'::'MTConnectStreams Response Document'::Header => target.hasHeader;
                end : MTConnectStreams;
            }
            part def MTConnectStreams {
                doc 
                /* root entity of an {{term(MTConnectStreams Response Document)}} that contains the {{term(Observation Information Model)}} of one or more {{block(Device)}} entities.
                 *
                 * ![MTConnectStreams](figures/MTConnectStreams.png "MTConnectStreams"){: width="0.8"}
                 *
                 * > Note: Additional properties of {{block(MTConnectStreams)}} **MAY** be defined for schema and namespace declaration. See {{sect(Schema and Namespace Declaration Information)}} for an {{term(XML)}} example.*/
                ref part hasHeader [1] : Fundamentals::'MTConnect Protocol'::'MTConnectStreams Response Document'::Header;
                part hasDeviceStream [0..*] : 'Observation Information Model'::DeviceStream;
            }
            part def Header {
                doc /* provides information from an {{term(agent)}} defining version information, storage capacity, and parameters associated with the data management within the {{term(agent)}}.*/
                attribute firstSequence [1] : Profile::DataTypes::uint64 {
                    doc /* {{term(sequence number)}} assigned to the oldest piece of {{term(streaming data)}} stored in the {{term(buffer)}} of the {{term(agent)}} immediately prior to the time that the {{term(agent)}} published the {{term(response document)}}.   */
                }
                attribute lastSequence [1] : Profile::DataTypes::uint64 {
                    doc 
                    /* {{term(sequence number)}} assigned to the last piece of {{term(streaming data)}} that was added to the {{term(buffer)}} of the {{term(agent)}} immediately prior to the time that the {{term(agent)}} published the {{term(response document)}}.   
                     *
                     */
                }
                attribute nextSequence [1] : Profile::DataTypes::uint64 {
                    doc 
                    /* {{term(sequence number)}} of the piece of {{term(streaming data)}} that is the next piece of data to be retrieved from the {{term(buffer)}} of the {{term(agent)}} that was not included in the {{term(response document)}} published by the {{term(agent)}}.
                     *
                     * If the {{term(streaming data)}} included in the {{term(response document)}} includes the last piece of data stored in the {{term(buffer)}} of the {{term(agent)}} at the time that the document was published, then the value reported for {{property(Header::nextSequence)}} **MUST** be equal to {{property(Header::lastSequence)}} + 1.*/
                }
                attribute version [1] : Profile::DataTypes::version {
                    doc 
                    /* {{term(major)}}, {{term(minor)}}, and {{term(revision)}} number of the MTConnect Standard that defines the {{term(semantic data model)}} that represents the content of the {{term(response document)}}. It also includes the revision number of the {{term(schema)}} associated with that specific {{term(semantic data model)}}.
                     *
                     * As an example, the value reported for {{property(Header::version)}} for a {{term(response document)}} that was structured based on {{term(schema)}} revision 10 associated with Version 1.4.0 of the MTConnect Standard would be:  1.4.0.10*/
                }
                attribute testIndicator [0..1] : Profile::DataTypes::boolean default false {
                    doc 
                    /* indicates whether the {{term(agent)}} that published the {{term(response document)}} is operating in a test mode.
                     *
                     * If {{property(Header::testIndicator)}} is not specified, the value for {{property(Header::testIndicator)}} **MUST** be interpreted to be `false`.*/
                }
                attribute sender [1] : Profile::DataTypes::string {
                    doc 
                    /* identification defining where the {{term(agent)}} that published the {{term(response document)}} is installed or hosted.
                     *
                     * {{property(Header::sender)}} **MUST** be either an IP Address or Hostname describing where the {{term(agent)}} is installed or the URL of the {{term(agent)}}; e.g., `http://<address>[:port]/`. 
                     *
                     * > Note:  The port number need not be specified if it is the default HTTP port 80.*/
                }
                attribute instanceId [1] : Profile::DataTypes::uint64 {
                    doc 
                    /* identifier for a specific instantiation of the {{term(buffer)}} associated with the {{term(agent)}} that published the {{term(response document)}}.  
                     *      
                     * {{property(Header::instanceId)}} **MUST** be changed to a different unique number each time the {{term(buffer)}} is cleared and a new set of data begins to be collected.*/
                }
                attribute creationTime [1] : Profile::DataTypes::datetime {
                    doc /* timestamp that an {{term(agent)}} published the {{term(response document)}}. */
                }
                attribute bufferSize [1] : Profile::DataTypes::uint32 {
                    doc 
                    /* maximum number of {{termplural(DataItem)}} that **MAY** be retained in the {{term(agent)}} that published the {{term(response document)}} at any point in time.
                     *
                     * > Note 1 to entry:  {{property(Header::bufferSize)}} represents the maximum number of sequence numbers that **MAY** be stored in the {{term(agent)}}. 
                     *
                     * > Note 2 to entry: The implementer is responsible for allocating the appropriate amount of storage capacity required to accommodate the {{property(Header::bufferSize)}}.
                     */
                }
                attribute deviceModelChangeTime [1] : Profile::DataTypes::datetime {
                    doc /* timestamp of the last update of the {{block(Device)}} information for any device.*/
                }
                private attribute validation [0..1] : Profile::DataTypes::boolean default false {
                    doc /* indicates if the {{term(MTConnect Agent)}} is validating against the normative model.*/
                }
            }
            doc /* This section provides semantic information for the {{block(MTConnectStreams)}} entity.*/
        }
        package 'MTConnectErrors Response Document' {
            part def MTConnectError {
                doc 
                /* root entity of an {{term(MTConnectErrors Response Document)}} that contains the {{term(Error Information Model)}}.
                 *
                 * ![MTConnectError](figures/MTConnectErrors.png "MTConnectError"){: width="0.8"}
                 *
                 * > Note: Additional properties of {{block(MTConnectError)}} **MAY** be defined for schema and namespace declaration. See {{sect(Schema and Namespace Declaration Information)}} for an {{term(XML)}} example.*/
                ref part hasHeader [1] : Header;
                part hasError [1..*] : Error;
                part error [1] : Error;
            }
            part def Header {
                doc /* provides information from an {{term(agent)}} defining version information, storage capacity, and parameters associated with the data management within the {{term(agent)}}.*/
                attribute bufferSize [1] : Profile::DataTypes::uint32 {
                    doc 
                    /* maximum number of {{termplural(DataItem)}} that **MAY** be retained in the {{term(agent)}} that published the {{term(response document)}} at any point in time.
                     *
                     * > Note 1 to entry:  {{property(Header::bufferSize)}} represents the maximum number of sequence numbers that **MAY** be stored in the {{term(agent)}}. 
                     *
                     * > Note 2 to entry: The implementer is responsible for allocating the appropriate amount of storage capacity required to accommodate the {{property(Header::bufferSize)}}.
                     */
                }
                attribute creationTime [1] : Profile::DataTypes::datetime {
                    doc /* timestamp that an {{term(agent)}} published the {{term(response document)}}. */
                }
                attribute instanceId [1] : Profile::DataTypes::uint64 {
                    doc 
                    /* identifier for a specific instantiation of the {{term(buffer)}} associated with the {{term(agent)}} that published the {{term(response document)}}.  
                     *      
                     * {{property(Header::instanceId)}} **MUST** be changed to a different unique number each time the {{term(buffer)}} is cleared and a new set of data begins to be collected.*/
                }
                attribute sender [1] : Profile::DataTypes::string {
                    doc 
                    /* identification defining where the {{term(agent)}} that published the {{term(response document)}} is installed or hosted.
                     *
                     * {{property(Header::sender)}} **MUST** be either an IP Address or Hostname describing where the {{term(agent)}} is installed or the URL of the {{term(agent)}}; e.g., `http://<address>[:port]/`. 
                     *
                     * > Note:  The port number need not be specified if it is the default HTTP port 80.*/
                }
                attribute testIndicator [0..1] : Profile::DataTypes::boolean default false {
                    doc 
                    /* indicates whether the {{term(agent)}} that published the {{term(response document)}} is operating in a test mode.
                     *
                     * If {{property(Header::testIndicator)}} is not specified, the value for {{property(Header::testIndicator)}} **MUST** be interpreted to be `false`.*/
                }
                attribute version [1] : Profile::DataTypes::version {
                    doc 
                    /* {{term(major)}}, {{term(minor)}}, and {{term(revision)}} number of the MTConnect Standard that defines the {{term(semantic data model)}} that represents the content of the {{term(response document)}}. It also includes the revision number of the {{term(schema)}} associated with that specific {{term(semantic data model)}}.
                     *
                     * As an example, the value reported for {{property(Header::version)}} for a {{term(response document)}} that was structured based on {{term(schema)}} revision 10 associated with Version 1.4.0 of the MTConnect Standard would be:  1.4.0.10*/
                }
                attribute firstSequence [0..1] : Profile::DataTypes::uint64 {
                    doc /* {{term(sequence number)}} assigned to the oldest piece of {{term(streaming data)}} stored in the {{term(buffer)}} of the {{term(agent)}} immediately prior to the time that the {{term(agent)}} published the {{term(response document)}}.   */
                }
                attribute lastSequence [0..1] : Profile::DataTypes::uint64 {
                    doc 
                    /* {{term(sequence number)}} assigned to the last piece of {{term(streaming data)}} that was added to the {{term(buffer)}} of the {{term(agent)}} immediately prior to the time that the {{term(agent)}} published the {{term(response document)}}.   
                     *
                     */
                }
                attribute nextSequence [0..1] : Profile::DataTypes::uint64 {
                    doc 
                    /* {{term(sequence number)}} of the piece of {{term(streaming data)}} that is the next piece of data to be retrieved from the {{term(buffer)}} of the {{term(agent)}} that was not included in the {{term(response document)}} published by the {{term(agent)}}.
                     *
                     * If the {{term(streaming data)}} included in the {{term(response document)}} includes the last piece of data stored in the {{term(buffer)}} of the {{term(agent)}} at the time that the document was published, then the value reported for {{property(Header::nextSequence)}} **MUST** be equal to {{property(Header::lastSequence)}} + 1.*/
                }
                attribute deviceModelChangeTime [1] : Profile::DataTypes::datetime {
                    doc /* timestamp of the last update of the {{block(Device)}} information for any device.*/
                }
            }
            connection def Header {
                end hasHeader : Header => target.hasHeader;
                private end : MTConnectError;
            }
            abstract part def Error {
                doc /* abstract error encountered by an {{term(agent)}} when responding to a {{term(request)}}.*/
                attribute errorCode [1] : Profile::DataTypes::ErrorCodeEnum {
                    doc /* descriptive code that indicates the type of error that was encountered by an {{term(agent)}}.*/
                }
                attribute value [0..1] : Profile::DataTypes::string {
                    doc /* textual description of the error and any additional information an {{term(agent)}} is capable of providing regarding a specific error.*/
                }
                private attribute URI [1] : Profile::DataTypes::string {
                    doc /* {{term(HTTP request)}}*/
                }
                private attribute ErrorMessage [0..1] : Profile::DataTypes::string {
                    doc /* possible reason for the {{term(MTConnectErrors Response Document)}}*/
                }
                private attribute Request [0..1] : Profile::DataTypes::string {
                    doc /* text of the invalid response document type.*/
                }
            }
            connection def Errors {
                end hasError : Error => target.hasError;
                doc 
                /* {{block(Errors)}} groups one or more {{block(Error)}} entities. See {{sect(Error)}}.
                 *
                 * > Note: When compatibility with Version 1.0.1 and earlier of the MTConnect Standard is required for an implementation, the {{term(MTConnectErrors Response Document)}} contains only a single {{block(Error)}} entity and the {{block(Errors)}} entity **MUST NOT** appear in the document.*/
                private end : MTConnectError;
            }
            connection def Error {
                end error : Error => target.error;
                private end : MTConnectError;
            }
            package 'Error Types' {
                part def InvalidParameterValue :> Error {
                    doc /* supplied value does not match the required type.*/
                    part hasQueryParameter : QueryParameter;
                    private attribute ErrorMessage [1] :>> Fundamentals::'MTConnect Protocol'::'MTConnectErrors Response Document'::Error::ErrorMessage : Profile::DataTypes::string {
                        doc /* possible reason for the {{term(MTConnectErrors Response Document)}}*/
                    }
                }
                part def InvalidXPath :> Error {
                    doc /* {{term(XPath)}} is either structurally malformed or the XPath does not exist.*/
                }
                part def QueryError :> Error {
                    doc 
                    /* agent was unable to interpret the query.
                     *
                     * The query parameters do not contain valid values or include an invalid parameter.*/
                }
                part def AssetNotFound :> Error {
                    doc /* request for information specifies an {{block(Asset)}} that is not recognized by the agent.*/
                    private attribute AssetId [1] : Profile::DataTypes::ID {
                        doc /* {{property(Asset::assetId)}} of the requested {{block(Asset)}}*/
                    }
                }
                part def TooMany :> Error {
                    doc 
                    /* `count` parameter provided in the {{term(request)}} for information requires either of the following:
                     *
                     * * {{term(streaming data)}} that includes more pieces of data than the {{term(agent)}} is capable of organizing in an {{term(MTConnectStreams Response Document)}}. 
                     *
                     * * {{block(Assets)}} that include more {{block(Asset)}} in an {{term(MTConnectAssets Response Document)}} than the {{term(agent)}} is capable of handling. */
                }
                part def Unsupported :> Error {
                    doc /* valid request was provided, but the agent does not support the feature or type of request.*/
                }
                part def InvalidURI :> Error {
                    doc /* {{term(URI)}} provided was incorrect.*/
                }
                part def InvalidRequest :> Error {
                    doc /* request contains information that was not recognized by the agent.*/
                    private attribute ErrorMessage [1] :>> Fundamentals::'MTConnect Protocol'::'MTConnectErrors Response Document'::Error::ErrorMessage : Profile::DataTypes::string {
                        doc /* possible reason for the {{term(MTConnectErrors Response Document)}}*/
                    }
                }
                part def InternalError :> Error {
                    doc /* agent experienced an error while attempting to publish the requested information.*/
                }
                part def NoDevice :> Error {
                    doc /* identity of the {{block(Device)}} specified in the request for information is not associated with the agent.*/
                }
                part def OutOfRange :> Error {
                    doc /* request for information specifies streaming data that includes sequence number(s) for pieces of data that are beyond the end of the buffer.*/
                    part hasQueryParameter : QueryParameter;
                }
                part def Unauthorized :> Error {
                    doc /* requester does not have sufficient permissions to access the requested information.*/
                }
                part def QueryParameter {
                    doc /* property of the {{term(HTTP Request)}} that modifies the information returned by the {{term(HTTP Request)}}.*/
                    private attribute name [1] : Profile::DataTypes::QueryParameterEnum {
                        doc /* name of the parameter.*/
                    }
                    private attribute Maximum [0..1] : Profile::DataTypes::double {
                        doc /* maximum allowed value.*/
                    }
                    private attribute Minimum [0..1] : Profile::DataTypes::double {
                        doc /* minimal allowed value.*/
                    }
                    private attribute Value [0..1] : Profile::DataTypes::string {
                        doc /* given value.*/
                    }
                    private attribute Type [0..1] : Profile::DataTypes::string {
                        doc /* expected datatype of the parameter.*/
                    }
                    private attribute Format [0..1] : Profile::DataTypes::string {
                        doc /* expected datatype format of the parameter.*/
                    }
                }
                part def InvalidQueryParameter :> Error {
                    doc /* agent does not recognize the parameter.*/
                    private attribute ErrorMessage [1] :>> Fundamentals::'MTConnect Protocol'::'MTConnectErrors Response Document'::Error::ErrorMessage : Profile::DataTypes::string {
                        doc /* possible reason for the {{term(MTConnectErrors Response Document)}}*/
                    }
                }
                connection def QueryParameter {
                    end hasQueryParameter : QueryParameter => target.hasQueryParameter;
                    private end : OutOfRange;
                }
                connection def QueryParameter {
                    end hasQueryParameter : QueryParameter => target.hasQueryParameter;
                    private end : InvalidParameterValue;
                }
                doc /* This section provides semantic information for the types of {block(Error)}}.*/
            }
            doc /* This section provides semantic information for the {{block(MTConnectErrors)}} entity.*/
            comment /* Error Information Model*/
            doc 
            /* The {{term(Error Information Model)}} establishes the rules and terminology that describes the {{term(response document)}} returned by an {{term(agent)}} when it encounters an error while interpreting a {{term(request)}} for information from a client software application or when an {{term(agent)}} experiences an error while publishing the {{term(response)}} to a {{term(request)}} for information.      
             *
             * An {{term(agent)}} provides the information regarding errors encountered when processing a {{term(request)}} for information by publishing an {{term(MTConnectErrors Response Document)}} to the client software application that made the {{term(request)}} for information.*/
        }
        package 'REST Protocol' {
            part def Agent {
                doc 
                /* {{term(agent)}}.
                 *
                 * An {{term(agent)}} **MUST** perform the following tasks:
                 *
                 * * Collect data from manufacturing equipment.
                 * * Generate {{termplural(response document)}}.
                 * * Provide a REST interface using {{term(HTTP)}}.
                 *
                 * In addition to {{term(XML)}} and {{term(HTTP)}}, An {{term(agent)}} **MAY** provide additional protocols and representations. Some representations **MAY** have companion specifications.*/
                attribute instanceId : Profile::DataTypes::uint32 {
                    doc 
                    /* identifier for an {{term(instance)}} of the {{term(agent)}}.
                     *      
                     * {{property(Header::instanceId)}} **MUST** be changed to a different unique number each time the {{term(buffer)}} is cleared and a new set of data begins to be collected.*/
                }
                attribute sequenceNumber : Profile::DataTypes::uint64 {
                    doc /* {{term(sequence number)}}.*/
                }
                attribute bufferSize : Profile::DataTypes::uint32 {
                    doc /* maximum number of {{termplural(Observation)}} that **MAY** be retained in the {{term(agent)}} that published the {{term(response document)}} at any point in time.*/
                }
                attribute maxAssets : Profile::DataTypes::uint32 {
                    doc /* maximum number of {{termplural(Asset)}} that **MAY** be retained in the {{term(agent)}} that published the {{term(response document)}} at any point in time.*/
                }
                attribute assetCount : Profile::DataTypes::uint32 {
                    doc /* current number of {{termplural(Asset)}} that are currently stored in the {{term(agent)}} as of the {{property(Header::creationTime)}} that the {{term(agent)}} published the {{term(response document)}}.*/
                }
                private occurrence : 'Reference Agent Architecture'::Source;
                part hasObservation [0..*] : 'Observation Information Model'::Observation;
                part hasAsset [0..*] : 'Asset Information Model'::Asset;
            }
            connection def buffer {
                end hasObservation : 'Observation Information Model'::Observation => target.hasObservation;
                doc /* `buffer` is a {{term(buffer)}} for {{block(Observation)}} types.*/
                private end : Agent;
            }
            connection def assetBuffer {
                end hasAsset : 'Asset Information Model'::Asset => target.hasAsset;
                doc /* `assetBuffer` is an {{term(asset buffer)}} for {{block(Asset)}} types.*/
                private end : Agent;
            }
            doc 
            /* An {{term(agent)}} **MUST** provide a REST API {{term(API)}} supporting HTTP version 1.0 or greater.  This interface **MUST** support HTTP (RFC7230) and use URIs (RFC3986) to identify specific information requested from an {{term(agent)}}. 
             *
             * The REST API adheres to the architectural principles of a stateless service to retrieve information associated with pieces of equipment. Additionally, the API is read-only and does not produce any side effects on the {{term(agent)}} or the equipment. In REST state management, the client is responsible for recovery in case of an error or loss of connection.
             *
             * ### HTTP Request
             *
             * An {{term(agent)}} **MUST** support the `HTTP` `GET` verb, all other verbs are optional. See IETF RFC 7230 for a complete description of the HTTP request structure.
             *
             * The HTTP uses Uniform Resource Identifiers (URI) as outlined in IETF RFC 3986 as the *request-target*. IETF RFC 7230 specifies the http URI scheme for the *request-target* as follows:
             *
             * 1. `protocol`: The protocol used for the request. Must be `http` or `https`.
             *
             * 2. `authority`: The network domain or address of the agent with an optional port.
             *
             * 3. `path`: A Hierarchical Identifier following a slash (`/`) and before the optional question-mark (`?`). The `path` separates segments by a slash (`/`).
             *
             * 4. `query`: The portion of the HTTP request following the question-mark (`?`). The query portion of the HTTP request is composed of key-value pairs, `<key>=<value>` separated by an ampersand (`&`).
             *
             * #### `path` Portion of an HTTP Request
             *
             * The `path` portion of the *request-target* has the following segments:
             *
             * * `device-name` or `uuid`: optional `name` or `uuid` of the {{block(Device)}}
             * * `request`: request, must be one of the following: (also see {{sect(Operations for Agent)}})
             *   - {{operation(REST Protocol::Agent::probe)}}
             *   - {{operation(REST Protocol::Agent::current)}}
             *   - {{operation(REST Protocol::Agent::sample)}}
             *   - {{operation(REST Protocol::Agent::asset)}}  or `assets`
             *     - {{operation(REST Protocol::Agent::asset)}} request has additional optional segment `<asset ids>`
             *   
             * If `name` or `uuid` segement are not specified in the {{term(HTTP Request)}}, an {{term(agent)}} **MUST** return information for all pieces of equipment. The following sections will 
             *
             * Examples: 
             *   
             * * `http://localhost:5000/my_device/probe`
             *   
             *     The request only provides information about `my_device`.
             *   
             * * `http://localhost:5000/probe`
             *
             *   The request provides information for all devices. 
             *
             * The following section specifies the details for each request.
             *
             * ### MTConnect REST API
             *
             * An {{term(agent)}} **MUST** support {{termplural(probe request)}}, {{termplural(current request)}}, {{termplural(sample request)}}, and {{termplural(asset request)}}.
             *
             * See the operations of the {{block(REST Protocol::Agent)}} for details regarding the {{termplural(request)}}.
             *
             * ### HTTP Errors
             *
             * When an {{term(agent)}} receives an {{term(HTTP Request)}} that is incorrectly formatted or is not supported by the {{term(agent)}}, the {{term(agent)}} **MUST** publish an {{term(HTTP Error Message)}} which includes a specific status code from the tables above indicating that the {{term(request)}} could not be handled by the {{term(agent)}}.
             *
             * Also, if the {{term(agent)}} experiences an internal error and is unable to provide the requested {{term(response document)}}, it **MUST** publish an {{term(HTTP Error Message)}} that includes a specific status code from the table above.
             *
             * When an {{term(agent)}} encounters an error in interpreting or responding to an {{term(HTTP Request)}}, the {{term(agent)}} **MUST** also publish an {{term(MTConnectErrors Response Document)}} that provides additional details about the error.  See {{sect(Error Information Model)}} for details on the {{term(MTConnectErrors Response Document)}}.  
             *
             * #### Streaming Data
             *
             * HTTP {{term(data streaming)}} is a method for an {{term(agent)}} to provide a continuous stream of {{termplural(observation)}} in response to a single {{term(request)}} using a {{term(publish and subscribe)}} communication pattern.
             *
             * When an {{term(HTTP Request)}} includes an `interval` parameter, an {{term(agent)}} **MUST** provide data with a minimum delay in milliseconds between the end of one data transmission and the beginning of the next.  A value of zero (0) for the `interval` parameter indicates that the {{term(agent)}} should deliver data at the highest rate possible and is only relevant for {{termplural(sample request)}} .
             *
             * The format of the response **MUST** use an `x-multipart-replace` encoded message with each section separated by MIME boundaries.  Each section **MUST** contain an entire {{term(MTConnectStreams Response Document)}}. 
             *
             * When streaming for a {{term(current request)}}, the {{term(agent)}} produces an {{term(MTConnectStreams Response Document)}} with the most current {{termplural(observation)}} every `interval` milliseconds.
             *
             * When streaming for a {{term(sample request)}}, if there are no available {{termplural(observation)}} after the `interval` time elapsed, the {{term(agent)}} **MUST** wait for either the `heartbeat` time to elapse or an {{term(observation)}} arrives. If the `heartbeat` time elapses and no {{termplural(observation)}} arrive, then an empty {{term(MTConnectStreams Response Document)}} **MUST** be sent.
             *
             * > Note: For more information on MIME, see IETF RFC 1521 and RFC 822.
             *
             * An example of the format for an {{term(HTTP Request)}} that  includes an `interval` parameter is:
             *
             * ~~~~
             * http://localhost:5000/sample?interval=1000
             * ~~~~
             * {: caption="Example for HTTP Request with interval parameter" label="example-for-http-request-with-interval-parameter"}
             *
             * HTTP Response Header:
             *
             * ~~~~
             * HTTP/1.1 200 OK
             * Connection: close
             * Date: Sat, 13 Mar 2010 08:33:37 UTC
             * Status: 200 OK
             * Content-Disposition: inline
             * X-Runtime: 144ms
             * Content-Type: multipart/x-mixed-replace;boundary=
             * a8e12eced4fb871ac096a99bf9728425
             * Transfer-Encoding: chunked
             * ~~~~
             * {: caption="HTTP Response header" label="http-response-header"}
             *
             * Lines 1-9 in {{lst(http-response-header)}} represent a standard header for a MIME `multipart/x-mixed-replace` message.  The boundary is a separator for each section of the stream. Lines 7-8 indicate this is a multipart MIME message and the boundary between sections. 
             *
             * With streaming protocols, the `Content-length` **MUST** be omitted and `Transfer-Encoding` **MUST** be set to `chunked` (line 9). See IETF RFC 7230 for a full description of the HTTP protocol and chunked encoding.
             *
             * ~~~~
             * --a8e12eced4fb871ac096a99bf9728425
             * Content-type: text/xml
             * Content-length: 887
             *
             * <?xml version="1.0" ecoding="UTF-8"?>
             * <MTConnectStreams ...>...
             * ~~~~
             * {: caption="HTTP Response header 2" label="http-response-header-2" start="last"}
             *
             * Each section of the document begins with a boundary preceded by two hyphens (`--`). The `Content-type` and `Content-length` header fields **MUST** be provided for each section and **MUST** be followed by `<CR><LF><CR><LF>` (ASCII code for `<CR>` is 13 and `<LF>` 10) before the {{term(XML)}} document. The header and the `<CR><LF><CR><LF>` **MUST NOT** be included in the computation of the content length.
             *
             * An {{term(agent)}} MUST continue to stream results until the client closes the connection. The {{term(agent)}} MUST NOT stop streaming for any reason other than the following:
             *
             * * {{term(agent)}} process stops
             * * The client application stops receiving data
             *
             * ##### Heartbeat
             *
             * When {{term(streaming data)}} is requested from a {{term(sample request)}}, an {{term(agent)}} **MUST** support a {{term(heartbeat)}} to indicate to a client application that the HTTP connection is still viable during times when there is no new data available to be published.  The {{term(heartbeat)}} is indicated by an {{term(agent)}} by sending an MTConnect {{term(response document)}} with an empty {{block(Steams)}} entity (See {{package(Observation Information Model)}} for more details on {{block(Streams)}}) to the client software application.
             *
             * The {{term(heartbeat)}} **MUST** occur on a periodic basis given by the optional `heartbeat` query parameter and **MUST** default to 10 seconds.  An {{term(agent)}} **MUST** maintain a separate {{term(heartbeat)}} for each client application for which the {{term(agent)}} is responding to a {{term(data streaming)}} {{term(request)}}.
             *
             * An {{term(agent)}} **MUST** begin calculating the interval for the time-period of the {{term(heartbeat)}} for each client application immediately after a {{term(response document)}} is published to that specific client application.
             *
             * The {{term(heartbeat)}} remains in effect for each client software application until the {{term(data streaming)}} {{term(request)}} is terminated by either the {{term(agent)}} or the client application.
             *
             * #### References
             *
             * A {{block(Component)}} **MAY** include a set of {{block(Reference)}} entities of the following types that **MAY** alter the content of the {{termplural(MTConnectStreams Response Document)}} published in response to a {{term(current request)}} or a {{term(sample request)}} as specified:
             *
             * * A {{term(Component)}} reference ({{block(ComponentRef)}}) modifies the set of {{termplural(Observation)}}, limited by a path query parameter of a {{term(current request)}} or {{term(sample request)}}, to include the {{termplural(Observation)}} associated with the entity whose value for its `id` attribute matches the value provided for the `idRef` attribute of the {{block(ComponentRef)}} element. Additionally, {{termplural(Observation)}} defined for any {{term(lower level)}} entity(s) associated with the identified entities **MUST** also be returned. The result is equivalent to appending `//[@id=<"idRef">]` to the path query parameters of the {{term(current request)}} or {{term(sample request)}}. See {{package(Agent)}} for more details on path queries.
             *
             * * A {{term(DataItem)}} reference ({{block(DataItemRef)}}) modifies the set of resulting {{termplural(Observation)}}, limited by a path query parameter of a {{term(current request)}} or {{term(sample request)}}, to include the {{termplural(Observation)}} whose value for its `id` attribute matches the value provided for the `idRef` attribute of the {{block(DataItemRef)}} element. The result is equivalent to appending `//[@id=<"idRef">]` to the path query parameters of the {{term(current request)}} or {{term(sample request)}}. See {{package(Agent)}} for more details on path queries.
             */
        }
        package 'MTConnectExceptionsReport Response Document' {
            abstract part def MTConnectExceptionsReport {
                doc /* root entity of an {{term(MTConnectExceptionsReport Response Document)}} that contains the {{term(ExceptionReport Information Model)}}.*/
            }
            part def MTConnectDevicesExceptionsReport :> MTConnectExceptionsReport {
                doc /* {{block(MTConnectExceptionsReport)}} where exception is encountered in the {{term(MTConnectDevices Response Document)}}.*/
                part hasMTConnectDevicesException [1..*] : Exception;
                part hasHeader : 'MTConnectDevices Response Document'::Header;
            }
            part def MTConnectStreamsExceptionsReport :> MTConnectExceptionsReport {
                doc /* {{block(MTConnectExceptionsReport)}} where exception is encountered in the {{term(MTConnectStreams Response Document)}}.*/
                part hasMTConnectStreamsException [1..*] : Exception;
                part hasHeader : 'MTConnectStreams Response Document'::Header;
            }
            part def MTConnectAssetsExceptionsReport :> MTConnectExceptionsReport {
                doc /* {{block(MTConnectExceptionsReport)}} where exception is encountered in the {{term(MTConnectAssets Response Document)}}.*/
                part hasMTConnectAssetsException [1..*] : Exception;
                part hasHeader : 'MTConnectAssets Response Document'::Header;
            }
            connection def Exceptions {
                end hasMTConnectDevicesException : Exception => target.hasMTConnectDevicesException;
                doc /* {{block(Exceptions)}} groups one or more {{block(Exception)}} entities. See {{sect(Exception)}}.
                 */
                private end : MTConnectDevicesExceptionsReport;
            }
            connection def Exceptions {
                end hasMTConnectStreamsException : Exception => target.hasMTConnectStreamsException;
                doc /* {{block(Exceptions)}} groups one or more {{block(Exception)}} entities. See {{sect(Exception)}}.
                 */
                private end : MTConnectStreamsExceptionsReport;
            }
            connection def Exceptions {
                end hasMTConnectAssetsException : Exception => target.hasMTConnectAssetsException;
                doc /* {{block(Exceptions)}} groups one or more {{block(Exception)}} entities. See {{sect(Exception)}}.
                 */
                private end : MTConnectAssetsExceptionsReport;
            }
            part def Exception {
                doc /* irregularity encountered by an {{term(agent)}} in a {{term(response document)}} that may or may not conform to the MTConnect Standard.*/
                private attribute severity [1] : Profile::DataTypes::SeverityEnum {
                    doc /* criticality associated with the exception.*/
                }
                private attribute code [1] : Profile::DataTypes::ExceptionCodeEnum {
                    doc /* identifier that indicates the type of exception encountered.*/
                }
                private attribute Message [1] : Profile::DataTypes::string;
                part hasTrace [1] : Trace;
            }
            part def Trace {
                doc /* information about the characteristics of the exception.*/
                private attribute Source [1] : Profile::DataTypes::string {
                    doc /* {{term(URI)}} of the artefact of where the exception occurred.*/
                }
                private attribute Context [1] : Profile::DataTypes::string {
                    doc /* unique path to the exception location.*/
                }
                private attribute ScopeType [1] : Profile::DataTypes::ScopeTypeEnum {
                    doc /* designates the exception property kind.*/
                }
                private attribute Scope [1] : Profile::DataTypes::string {
                    doc /* name of the property.*/
                }
                private attribute Value [0..1] : Profile::DataTypes::string {
                    doc /* given value of the property.*/
                }
                private attribute ExpectedType [0..1] : Profile::DataTypes::string {
                    doc /* normative value type for the property.*/
                }
            }
            connection def Trace {
                end hasTrace : Trace => target.hasTrace;
                private end : Exception;
            }
            connection def Header {
                end hasHeader : 'MTConnectDevices Response Document'::Header => target.hasHeader;
                private end : MTConnectDevicesExceptionsReport;
            }
            connection def Header {
                end hasHeader : 'MTConnectStreams Response Document'::Header => target.hasHeader;
                private end : MTConnectStreamsExceptionsReport;
            }
            connection def Header {
                end hasHeader : 'MTConnectAssets Response Document'::Header => target.hasHeader;
                private end : MTConnectAssetsExceptionsReport;
            }
            doc /* This section provides semantic information for the {{block(MTConnectExceptionsReport)}} entity.*/
        }
        doc 
        /* The {{term(agent)}} **MUST** support the {{package(REST Protocol)}} and produce {{term(XML)}} representations of the information models. 
         *
         * All other protocols and representations are optional.
         */
    }
    doc 
    /* The MTConnect Standard defines the normative information model and protocol for retrieving information from manufacturing equipment. This document specifies the {{term(agent)}} behavior and protocol.
     *
     * ## Agent
     *
     * The MTConnect Standard specifies the minimum functionality of the {{term(agent)}}. The functionality is as follows:
     *
     * * Provides store and forward messaging middleware service.
     * * Provides key-value information storage and asset retrieval service.
     * * Implements the REST API for the MTConnect Standard (See {{package(REST Protocol)}}).
     *   * {{term(Device)}} metadata.
     *   * {{termplural(observation)}} collected by the agent.
     *   * {{termplural(asset)}} collected by the agent.
     *
     * There are three types of information stored by an {{term(agent)}} that **MAY** be published in a {{term(response document)}}. These are as follows:
     *
     * * {{term(equipment metadata)}} specified in {{package(Device Information Model)}}.
     * * {{term(streaming data)}} provides the {{termplural(observation)}} specified in {{package(Observation Information Model)}}.
     * * {{termplural(Asset)}} specified in {{package(Asset Information Model)}}.
     *
     * ### Agent Instance ID
     *
     * The {{term(agent)}} **MUST** set the `instanceId` to a unique value whenever the {{term(sequence number)}} in the agent is initialized to `1`.  (see {{sect(Sequence Numbers)}} and {{sect(Persistence and Recovery)}} below). 
     *
     * ### Storage of Equipment Metadata
     *
     * An {{term(agent)}} **MUST** be capable of publishing {{term(equipment metadata)}} for the {{term(agent)}} as specified in {{package(Device Information Model)}}.
     *
     * ### Storage of Streaming Data
     *
     * The {{term(agent)}} **MAY** implement a {{term(buffer)}} with a fixed number of {{termplural(observation)}}. If the `bufferSize` is fixed, the {{term(agent)}} **MUST** store {{termplural(observation)}} using a first-in-first-out pattern. The {{term(agent)}} will remove the oldest {{term(observation)}} when the {{term(buffer)}} is full and a new {{term(observation)}} arrives.
     *
     * ![Data Storage in Buffer](figures/data-storage-in-buffer.png "data-storage-in-buffer"){: width="0.8"}
     *
     * In {{figure(first-in-first-out-buffer-management)}}, the maximum number of {{termplural(observation)}} that can be stored in the {{term(buffer)}} of the {{term(agent)}} is 8. The `bufferSize` in the header reports the maximum number of {{termplural(observation)}}. This example illustrates that when the {{term(buffer)}} fills up, the oldest piece of data falls out the other end.
     *
     * ![First In First Out Buffer Management](figures/first-in-first-out-buffer-management.png "first-in-first-out-buffer-management"){: width="0.8"}
     *
     * > Note: As an implementation suggestion, the {{term(buffer)}} should be sized large enough to provide a continuous stream of {{termplural(observation)}}. The implementer should also consider the impact of a temporary loss of communications when determining the size for the {{term(buffer)}}. A larger {{term(buffer)}} will allow more time to reconnect to an {{term(agent)}} without losing data.
     *
     * #### Sequence Numbers
     *
     * In an {{term(agent)}}, each occurrence of an {{term(observation)}} in the {{term(buffer)}} will be assigned a monotonically increasing unsigned 64-bit integer ({{term(sequence number)}}) when it arrives. The first {{term(sequence number)}} **MUST** be `1`.
     *
     * The {{term(sequence number)}} for each {{term(observation)}} **MUST** be unique for an instance of an {{term(agent)}} identified by an `instanceId`.
     *
     * {{table(instanceid-and-sequence)}} illustrates the changing of the `instanceId` when an {{term(agent)}} resets the {{term(sequence number)}} to `1`.
     *
     * | `instanceId` | `sequence` | 
     * |-------------:|-----------:|
     * |{{rowspan(5)}} 234556|234|
     * ||235|
     * ||236|
     * ||237|
     * ||238|
     * |{{span(2)}} Agent Stops and Restarts|
     * |{{rowspan(5)}} 234557|1|
     * ||2|
     * ||3|
     * ||4|
     * ||5|
     * {: caption="instanceId and sequence" label="instanceid-and-sequence" }
     *
     * {{figure(identifying-the-range-of-data-with-firstsequence-and-lastsequence)}} shows two additional pieces of information defined for an {{term(agent)}}:
     *
     * * `firstSequence` -- the oldest {{term(observation)}} in the {{term(buffer)}}. The {{term(agent)}} removes this {{term(observation)}} when it receives the next {{term(observation)}}
     *
     * * `lastSequence` -- the newest {{term(observation)}} in the {{term(buffer)}}
     *
     * `firstSequence` and `lastSequence` provide the range of values for the REST API requests.
     *
     * ![Indentifying the range of data with firstSequence and lastSequence](figures/identifying-the-range-of-data-with-firstsequence-and-lastsequence.png "identifying-the-range-of-data-with-firstsequence-and-lastsequence"){: width="0.75"}
     *
     * The {{term(agent)}} **MUST** begin evaluating {{termplural(observation)}} with {{term(sample request)}}'s `from` parameter. Also, the {{term(agent)}}  **MUST** include a maximum number of {{termplural(observation)}} given by the `count` parameter in the {{term(response document)}}.
     *
     * In {{figure(identifying-the-range-of-data-with-from-and-count)}}, the request specifies the {{termplural(observation)}} start at {{term(sequence number)}} `15` (`from`) and includes a total of three items (`count`).
     *
     * ![Identifying the range of data with from and count](figures/identifying-the-range-of-data-with-from-and-count.png "identifying-the-range-of-data-with-from-and-count"){: width="0.75"}
     *
     * `nextSequence` header property has the {{term(sequence number)}} of the next {{term(observation)}} in the {{term(buffer)}} for subsequent {{termplural(sample request)}} providing a contiguous set of {{termplural(observation)}}. In the example in {{figure(identifying-the-range-of-data-with-from-and-count)}}, the next {{term(sequence number)}} (`nextSequence`) will be 18.
     *
     * As shown in {{figure(identifying-the-range-of-data-with-nextsequence-and-lastsequence)}}, the combination of `from` and `count` defined by the {{term(request)}} indicates a {{term(sequence number)}} for data that is beyond that which is currently in the {{term(buffer)}}. In this case, `nextSequence` is set to a value of $$ lastSequence + 1 $$.
     *
     * ![Indentifying the range of data with nextSequence and lastSequence](figures/identifying-the-range-of-data-with-nextsequence-and-lastsequence.png "identifying-the-range-of-data-with-nextsequence-and-lastsequence"){: width="0.75"}
     *
     * #### Observation Buffer
     *
     * An {{term(observation)}} has four pieces of information as follows:
     *
     * 1. {{term(sequence number)}} associated with each {{term(observation)}} - `sequence`.
     * 2. The `timestamp` the {{term(observation)}} was made. .
     * 3. A reference to the `dataitemid` from the {{package(Device Information Model)}}.
     * 4. The value of the {{term(observation)}}.
     *
     * {{table(data-storage-concept)}} is an example demonstrating the concept of how data may be stored in an {{term(agent)}}:
     *
     * | `sequence` | `timestamp` | `dataItemId` | `result` |
     * |-----------:|------------:|-------------:|---------:|
     * |`101`|`2016-12-13T09:44:00.2221Z`|`AVAIL-28277`|`UNAVAILABLE`|
     * |`102`|`2016-12-13T09:54:00.3839Z`|`AVAIL-28277`|`AVAILABLE`|
     * |`103`|`2016-12-13T10:00:00.0594Z`|`POS-Y-28277`|`25.348`|
     * |`104`|`2016-12-13T10:00:00.0594Z`|`POS-Z-28277`|`13.23`|
     * |`105`|`2016-12-13T10:00:03.2839Z`|`SS-28277`|`0`|
     * |`106`|`2016-12-13T10:00:03.2839Z`|`POS-X-28277`|`11.195`|
     * |`107`|`2016-12-13T10:00:03.2839Z`|`POS-Y-28277`|`24.938`|
     * |`108`|`2016-12-13T10:01:37.8594Z`|`POS-Z-28277`|`1.143`|
     * |`109`|`2016-12-13T10:02:03.2617Z`|`SS-28277`|`1002`|
     * {: caption="Data Storage Concept" label="data-storage-concept" }
     *
     * #### Timestamp
     *
     * {{termplural(observation)}} **MUST** have a `timestamp` giving the most accurate time that the {{term(observation)}} occurred.
     *
     * The timezone of the `timestamp` **MUST** be UTC (Coordinated Universal Time)  and represented using ISO 8601 format: e.g., "2010-04-01T21:22:43Z".
     *
     * Applications **SHOULD** use the {{term(observation)}}'s `timestamp` for ordering as opposed to {{term(sequence number)}}.
     *
     * All {{termplural(observation)}} occurring at the same time **MUST** have the same `timestamp`. 
     *
     * #### Recording Occurrences of Streaming Data
     *
     * The {{term(agent)}} **MUST** only place {{termplural(observation)}} in the {{term(buffer)}} if the data has changed from the previous {{term(observation)}} for the same {{block(DataItem)}}. 
     *
     * The {{term(agent)}} **MUST** place every {{term(observation)}} in the {{term(buffer)}}, without checking for changes, in the following cases:
     *
     * * The {{property(DataItem::discrete)}} is `true`. 
     * * The {{property(DataItem::representation)}} is `DISCRETE`.
     * * The {{property(DataItem::representation)}} is `TIME_SERIES`.
     *
     * #### Maintaining Last Value for Data Entities
     *
     * An {{term(agent)}} **MUST** retain the most recent {{term(observation)}} associated with each {{block(DataItem)}}, even if the {{term(observation)}} is no longer in the {{term(buffer)}}. This function supports the {{term(current request)}} functionality.
     *
     * #### Unavailability of Data
     *
     * An {{term(observation)}} with the value of `UNAVAILABLE` indicates the value is indeterminate.
     *
     * The {{term(agent)}} **MUST** initialize every {{block(DataItem)}}, unless it has a constant value (see below), with an {{term(observation)}} with the value of `UNAVAILABLE`. Aditionally, whenever the data source is unreachable, every {{block(DataItem)}} associated with the data source must have an {{term(observation)}} with the value of `UNAVAILABLE` and `timestamp` when the connection was lost. 
     *
     * An {{block(DataItem)}} that is constrained to a constant value, as defined in {{package(Device Information Model)}}, **MUST** only have an {{term(observation)}} with the constant value and **MUST NOT** be set to `UNAVAILABLE`.
     *
     * #### Persistence and Recovery
     *
     * The {{term(agent)}} **MAY** have a fixed size {{term(buffer)}} and the {{term(buffer)}} **MAY** be ephemeral.
     *
     * If the {{term(buffer)}} is recoverable, the {{term(agent)}} **MUST NOT** change the `instanceId` and **MUST NOT** set the {{term(sequence number)}} to `1`. The {{term(sequence number)}} **MUST** be one greater than the maximum value of the recovered {{termplural(observation)}}. $$ max(sequence) + 1 $$
     *
     * ### Storage of MTConnect Assets
     *
     * An {{term(agent)}} **MAY** only retain a limited number of {{block(Asset)}}s in the {{term(asset buffer)}}. The {{block(Asset)}}s are stored in first-in-first-out method where the oldest {{block(Asset)}} is removed when the {{term(asset buffer)}} is full and a new {{block(Asset)}} arrives.
     *
     * {{figure(first-in-first-out-asset-buffer-management)}} illustrates the oldest {{block(Asset)}} being removed from the {{term(asset buffer)}} when a new {{block(Asset)}} is added and the {{term(asset buffer)}} is full:
     *
     * ![First In First Out Asset Buffer Management](figures/first-in-first-out-asset-buffer-management.png "first-in-first-out-asset-buffer-management"){: width="0.6"}
     *
     * {{block(Asset)}}s are indexed by {{property(Asset::assetId)}}. In the case of {{block(Asset)}}s, {{figure(relationship-between-assetid-and-stored-asset-documents)}} demonstrates the relationship between the key ({{property(Asset::assetId)}}) and the stored {{block(Asset)}}:
     *
     * ![Relationship between assetId and stored Asset documents](figures/relationship-between-assetid-and-stored-asset-documents.png "relationship-between-assetid-and-stored-asset-documents"){: width="0.25"}
     *
     * > Note: The key ({{property(Asset::assetId)}}) is independent of the order of the {{block(Asset)}} stored in the {{term(asset buffer)}}.
     *
     * When the {{term(agent)}} receives a new {{block(Asset)}}, one of the following rules **MUST** apply:
     *
     * * If the {{block(Asset)}} is not in the {{term(asset buffer)}}, the {{term(agent)}} **MUST** add the new {{block(Asset)}} to the front of the {{term(asset buffer)}}. If the {{term(asset buffer)}} is full, the oldest {{block(Asset)}} will be removed from the {{term(asset buffer)}}.
     *
     * * If the {{block(Asset)}} is already in the {{term(asset buffer)}}, the {{term(agent)}} **MUST** replace the existing {{block(Asset)}} and move the {{block(Asset)}} to the front of the {{term(asset buffer)}}. 
     *
     * The number of {{block(Asset)}} that may be stored in an {{term(agent)}} is defined by the value for {{property(Header::assetBufferSize)}}. An {{property(Header::assetBufferSize)}} of 4,294,967,296 or $$ 2^{32 } $$ **MUST** indicate unlimited storage.
     *
     * The {{term(asset buffer)}} **MAY** be ephemeral and the {{block(Asset)}} entities will be lost if the {{term(agent)}} clears the {{term(asset buffer)}}. They must be recovered from the data source.
     *
     * {{package(Asset Information Model)}} provides additional information on {{term(asset)}} management. 
     *
     * ## Response Documents
     *
     * {{termplural(response document)}} are electronic documents generated by an {{term(agent)}} in response to a {{term(request)}} for data. 
     *
     * The {{termplural(response document)}} defined in the MTConnect Standard are:
     *
     * * {{term(MTConnectDevices Response Document)}}: Describes the composition and configuration of the {{term(Device)}} and the data that can be observed. See {{package(MTConnectDevices Response Document)}} and {{package(Device Information Model)}} for details on this information model.
     *
     * * {{term(MTConnectStreams Response Document)}}: {{termplural(Observation)}} made at a point in time about related {{termplural(DataItem)}}. See {{package(MTConnectStreams Response Document)}} and {{package(Observation Information Model)}} for details on this information model.
     *
     * * {{term(MTConnectAssets Response Document)}}: {{termplural(Asset)}}  related to {{termplural(Device)}}. See {{package(MTConnectAssets Response Document)}} and {{package(Asset Information Model)}} for details on this information model.
     *
     * * {{term(MTConnectErrors Response Document)}}: Information in response to a failed request. See {{package(MTConnectErrors Response Document)}} for details on this information model.
     *
     * ## Request/Response Information Exchange
     *
     * The transfer of information between an {{term(agent)}} and a client software application is based on a {{term(request and response)}} REST protocol. A client application requests specific information from an {{term(agent)}} and an {{term(agent)}} responds with a {{term(response document)}}.
     *
     * There are four types of {{termplural(MTConnect Request)}}. These {{termplural(request)}} are as follows:
     *
     * * {{term(probe request)}}: Requests information about one more more {{termplural(Device)}} as an {{block(MTConnectDevices)}} block.
     *
     * * {{term(current request)}}: Requests the most recent, or snapshot at a {{term(sequence number)}}, {{termplural(observation)}} as an {{block(MTConnectStreams)}} block.
     *
     * * {{term(sample request)}}: Requests a series of {{termplural(observation)}} as an {{block(MTConnectStreams)}} block.
     *
     * * {{term(asset request)}}: Requests a set of {{termplural(asset)}} as an {{block(MTConnectAssets)}} block.
     *
     * If an {{term(agent)}} is unable to respond to the request for information or the request includes invalid information, the {{term(agent)}} will publish an {{term(MTConnectErrors Response Document)}}. See {{block(MTConnectErrors)}}.
     *
     * See {{package(REST Protocol)}} for the details on the normative requirements of the agent.*/
    comment /* Fundamentals Appendix*/
    doc 
    /* {{newpage()}} 
     *
     * ## Fundamentals of Using XML to Encode Response Documents
     *
     * The MTConnect Standard specifies the structures and constructs that are used to encode {{termplural(response document)}}.  When these {{termplural(response document)}} are encoded using XML, there are additional rules defined by the XML standard that apply for creating an XML compliant document.  An implementer should refer to the W3C website for additional information on XML documentation and implementation details - http://www.w3.org/XML.
     *
     * The following provides specific terms and guidelines referenced in the MTConnect Standard for forming {{termplural(response document)}} with XML:  
     *
     *
     * * `tag`:  A `tag` is an XML construct that forms the foundation for an XML expression.  It defines the scope (beginning and end) of an XML expression.  The main types of tags are: 
     *
     * * `start-tag`:  Designates the beginning on an XML element; e.g., <{{term(element name)}}> 
     *
     * * `end-tag`:  Designates the end on an XML element; e.g., </{{term(element name)}}>. 
     *
     *
     * > Note: If an element has no {{termplural(child element)}} or {{term(CDATA)}}, the `end-tag` may be shortened to />.
     *
     *
     * * `Element`:  An element is an XML statement that is the primary building block for a document encoded using XML.  An element begins with a `start-tag` and ends with a matching `end-tag`.  The characters between the `start-tag` and the `end-tag` are the element's content.  The content may contain attributes, {{term(CDATA)}}, and/or other elements.  If the content contains additional elements, these elements are called {{termplural(child element)}}.
     *
     * An example would be:  <{{term(element name)}}>Content of the Element</{{term(element name)}}>.
     *
     * * {{term(child element)}}:  An XML element that is contained within a higher-level {{term(parent element)}}.  A {{term(child element)}} is also known as a sub-element.  XML allows an unlimited hierarchy of {{term(parent element)}}-{{term(child element)}} relationships that establishes the structure that defines how the various pieces of information in the document relate to each other.  A {{term(parent element)}} may have multiple associated {{termplural(child element)}}.
     *
     * * {{term(element name)}}:  A descriptive identifier contained in both the `start-tag` and `end-tag` that provides the name of an XML element.
     *
     * * `Attribute`:  A construct consisting of a name–value pair that provides additional information about that XML element.  The format for an attribute is `name="value"; where the value for the attribute is enclosed in a set of quotation (“) marks.  An XML attribute **MUST** only have a single value and each attribute can appear at most once in each element.  Also, each attribute **MUST** be defined in a {{term(schema)}} to either be required or optional.   
     *
     * * An example of attributes for an XML element is {{lst(example-of-attributes-for-an-element)}}:
     *
     * ~~~~xml
     * <DataItem category="SAMPLE" id="S1load"
     *   nativeUnits="PERCENT"  type="LOAD"
     *   units="PERCENT"/>
     * ~~~~
     * {: caption="Example of attributes for an element"}
     *
     * In this example, {{block(DataItem)}} is the {{term(element name)}}.  `category`, `id`, `nativeUnits`, `type`, and `units` are the names of the attributes.  “`SAMPLE`", “`S1load`", “`PERCENT`", “`LOAD`", and “`PERCENT`" are the values for each of the respective attributes.
     *
     * * {{term(CDATA)}}:  {{term(CDATA)}} is an XML term representing *Character Data*. *Character Data* contains a value(s) or text that is associated with an XML element.  {{term(CDATA)}} can be restricted to certain formats, patterns, or words.  
     *
     * An example of {{term(CDATA)}} associated with an XML element would be {{lst(example-of-cdata-associated-with-element)}}:
     *
     * ~~~~xml
     * <Message id="M1">This is some text</Message>
     * ~~~~
     * {: caption="Example of cdata associated with element"}
     *
     * In this example, `Message` is the {{term(element name)}} and `This is some text` is the {{term(CDATA)}}.
     *
     * * {{term(namespace)}}:  An XML {{term(namespace)}} defines a unique vocabulary for named elements and attributes in an XML document.  An XML document may contain content that is associated with multiple {{termplural(namespace)}}.  Each {{term(namespace)}} has its own unique identifier. 
     *
     * Elements and attributes are associated with a specific {{term(namespace)}} by placing a prefix on the name of the element or attribute that associates that name to a specific {{term(namespace)}}; e.g., `x:MyTarget` associates the element name `MyTarget` with the {{term(namespace)}} designated by `x:` (the prefix).
     *
     * {{termplural(namespace)}} are used to avoid naming conflicts within an XML document.  The naming convention used for elements and attributes may be associated with either the default {{term(namespace)}} specified in the header of an XML document or they may be associated with one or more alternate {{termplural(namespace)}}.  All elements or attributes associated with a {{term(namespace)}} that is not the default {{term(namespace)}}, must include a prefix (e.g., x:) as part of the name of the element or attribute to associate it with the proper {{term(namespace)}}.  See {{sect(Schema and Namespace Declaration Information)}} for details on the structure for XML headers.
     *
     * The names of the elements and attributes declared in a {{term(namespace)}} may be identified with a different prefix than the prefix that signifies that specific {{term(namespace)}}.  These prefixes are called {{term(namespace)}} aliases.  As an example, MTConnect Standard specific {{termplural(namespace)}} are designated as `m:` and the names of the elements and attributes defined in that {{term(namespace)}} have an alias prefix of `mt:` which designates these names as MTConnect Standard specific vocabulary; e.g., `mt:MTConnectDevices`. 
     *
     *
     * XML documents are encoded with a hierarchy of elements.  In general, XML elements may contain {{termplural(child element)}}, {{term(CDATA)}}, or both.  However, in the MTConnect Standard, an element **MUST NOT** contain mixed content; meaning it cannot contain both {{termplural(child element)}} and {{term(CDATA)}}. 
     *
     * The {{term(semantic data model)}} defined for each {{term(response document)}} specifies the elements and {{termplural(child element)}} that may appear in a document.  The {{term(semantic data model)}} also defines the number of times each element and {{term(child element)}} may appear in the document.
     *
     * {{lst(example-of-hierarchy-of-xml-elements)}} demonstrates the hierarchy of XML elements and {{termplural(child element)}} used to form an XML document:
     *
     * ~~~~xml
     * <Root Level>    (Parent Element)
     *   <First Level>  (Child Element to Root Level and 
     *   Parent Element to Second Level)
     *     <Second Level>  (Child Element to First Level
     *     and Parent Element to Third Level)
     *       <Third Level name="N1"></Third Level>  
     *       (Child Element to Second Level)
     *       <Third Level name="N2"></Third Level>  
     *       (Child Element to Second Level)
     *       <Third Level name="N3"></Third Level>  
     *       (Child Element to Second Level)
     *     </Second Level>   (end-tag for Second Level)
     *   </First Level>   (end-tag for First Level)
     * </Root Level>   (end-tag for Root Level)
     * ~~~~
     * {: caption="Example of hierarchy of XML elements"}
     *
     *
     * In the {{lst(example-of-hierarchy-of-xml-elements)}}, *Root Level* and *First Level* have one {{term(child element)}} (sub-elements) each and Second Level has three {{termplural(child element)}}; each called *Third Level*.  Each *Third Level* element has a different name attribute.  Each level in the structure is an element and each lower level element is a {{term(child element)}}.
     *
     * {{newpage()}}
     *
     * ## Schema and Namespace Declaration Information
     *
     * There are four pseudo-attributes typically included in the header of a {{term(response document)}} that declare the {{term(schema)}} and {{term(namespace)}} for the document.  Each of these pseudo-attributes provides specific information for a client software application to properly interpret the content of the {{term(response document)}}.
     *
     * The pseudo-attributes include:
     *
     * * `xmlns:xsi` – The `xsi` portion of this attribute name stands for {{term(XML Schema)}} instance.  An {{term(XML Schema)}} instance provides information that may be used by a software application to interpret XML specific information within a document.  See the W3C website for more details on `xmlns:xsi`.
     *
     * * `xmlns` – Declares the default {{term(namespace)}} associated with the content of the {{term(response document)}}.  The default {{term(namespace)}} is considered to apply to all elements and attributes whenever the name of the element or attribute does not contain a prefix identifying an alternate {{term(namespace)}}.
     *
     * The value of this attribute is an URN identifying the name of the file that defines the details of the {{term(namespace)}} content.  This URN provides a unique identify for the {{term(namespace)}}.
     *
     * * `xmlns:m` – Declares the MTConnect specific {{term(namespace)}} associated with the content of the {{term(response document)}}.  There may be multiple {{termplural(namespace)}} declared for an XML document.  Each may be associated to the default {{term(namespace)}} or it may be totally independent.  The `:m` designates that this is a specific MTConnect {{term(namespace)}} which is directly associated with the default {{term(namespace)}}.
     *
     *  
     * > Note:	See {{sect(Extensibility)}} for details regarding extended {{termplural(namespace)}}.
     *
     *
     * The value associated with this attribute is an URN identifying the name of the file that defines the details of the {{term(namespace)}} content.
     *
     * * `xsi:schemaLocation` -  Declares the name for the {{term(schema)}} associated with the {{term(response document)}} and the location of the file that contains the details of the {{term(schema)}} for that document.
     *
     * The value associated with this attribute has two parts:
     *
     *   * A URN identifying the name of the specific {{term(XML Schema)}} instance associated with the {{term(response document)}}.
     *
     *   * The path to the location where the file describing the specific {{term(XML Schema)}} instance is located.  If the file is located in the same root directory where the {{term(agent)}} is installed, then the local path MAY be declared.  Otherwise, a fully qualified URL must be declared to identify the location of the file.
     *
     *
     * > Note:	In the format of the value associated with `xsi:schemaLocation`, the URN and the path to the {{term(schema)}} file **MUST** be separated by a “space”.
     *
     *
     * In {{lst(example-of-schema-and-namespace-declaration)}}, the first line is the XML declaration.  The second line is a {{term(root element)}} called `MTConnectDevices`.  The remaining four lines are the pseudo-attributes of `MTCconnectDevices` that declare the XML {{term(schema)}} and {{term(namespace)}} associated with an {{term(MTConnectDevices Response Document)}}.
     *
     * ~~~~xml
     * <?xml version="1.0" encoding="UTF-8"?>
     *   <MTConnectDevices
     *    xmlns:xsi=http://www.w3.org/2001/XMLSchema-instance
     *    xmlns="urn:mtconnect.org:MTConnectDevices:1.3"
     *    xmlns:m="urn:mtconnect.org:MTConnectDevices:1.3"
     *    xsi:schemaLocation="urn:mtconnect.org:
     *     MTConnectDevices:1.3 /schemas/MTConnectDevices\_1.3.xsd">
     * ~~~~
     * {: caption="Example of schema and namespace declaration"}
     *
     * The format for the values provided for each of the pseudo-attributes **MUST** reference the {{term(semantic data model)}} (e.g., `MTConnectDevices`, `MTConnectStreams`, `MTConnectAssets`, or `MTConnectError`) and the version (i.e.; `1.1`, `1.2`, `1.3`, etc.) of the MTConnect Standard that depict the {{term(schema)}} and {{term(namespace)}}(s) associated with a specific {{term(response document)}}.
     *
     * When an implementer chooses to extend an MTConnect {{term(data model)}} by adding custom data types or additional {{termplural(structural element)}}, the {{term(schema)}} and {{term(namespace)}} for that {{term(data model)}} should be updated to reflect the additional content.  When this is done, the {{term(namespace)}} and {{term(schema)}} information in the header should be updated to reflect the URI for the extended {{term(namespace)}} and {{term(schema)}}. 
     *
     * {{newpage()}}
     *
     * ## Extensibility
     *
     * MTConnect is an extensible standard, which means that implementers **MAY** extend the {{termplural(data model)}} defined in the various sections of the MTConnect Standard to include information required for a specific implementation.  When these {{termplural(data model)}} are encoded using XML, the methods for extending these {{termplural(data model)}} are defined by the rules established for extending any XML schema (see the W3C website for more details on extending XML data models).
     *
     * The following are typical extensions that **MAY** be considered in the MTConnect {{termplural(data model)}}:
     *
     * * Additional `type` and `subtype` values for {{termplural(DataItem)}}.
     *
     * * Additional {{termplural(structural element)}} as containers.
     *
     * * Additional {{block(Composition)}} elements.
     *
     * * New {{block(Asset)}} types that are sub-typed from the abstract {{block(Asset)}} type.
     *
     * * {{termplural(child element)}} that may be added to specific XML elements contained within the {{termplural(MTConnect Information Model)}}.  These extended elements **MUST** be identified in a separate {{term(namespace)}}.
     *
     *
     * When extending an MTConnect {{term(data model)}}, there are some basic rules restricting changes to the MTConnect {{termplural(data model)}}.
     *
     * When extending an MTConnect {{term(data model)}}, an implementer:
     *
     * * **MUST NOT** add new value for category for {{termplural(DataItem)}},
     *
     * * **MUST NOT** add new {{termplural(root element)}},
     *
     * * **SHOULD NOT** add new {{term(top level)}} {{termplural(Component)}}, and
     *
     * * **MUST NOT** add any new attributes or include any sub-elements to {{block(Composition)}}.
     *
     * > Note:  Throughout the documents additional information is provided where extensibility may be acceptable or unacceptable to maintain compliance with the MTConnect Standard.
     *
     * When a {{term(schema)}} representing a {{term(data model)}} is extended, the {{term(schema)}} and {{term(namespace)}} declaration at the beginning of the corresponding {{term(response document)}} **MUST** be updated to reflect the new {{term(schema)}} and {{term(namespace)}} so that a client software application can properly validate the {{term(response document)}}.
     *
     * An XML example of a {{term(schema)}} and {{term(namespace)}} declaration, including an extended {{term(schema)}} and {{term(namespace)}}, is shown in {{lst(example-of-extended-schema-and-namespace-in-declaration)}}:
     *
     * ~~~~xml
     * <?xml version="1.0" encoding="UTF-8"?>
     *   <MTConnectDevices
     *    xmlns:xsi=http://www.w3.org/2001/XMLSchema-instance
     *    xmlns="urn:mtconnect.org:MTConnectDevices:1.3"
     *    xmlns:m="urn:mtconnect.org:MTConnectDevices:1.3"
     *    xmlns:x="urn:MyLocation:MyFile:MyVersion"
     *    xsi:schemaLocation="urn:MyLocation:MyFile:MyVersion
     *      /schemas/MyFileName.xsd" />
     * ~~~~
     * {: caption="Example of extended schema and namespace in declaration"}
     *
     * In this example:
     *
     * * `xmlns:x` is added in Line 6 to identify the {{term(XML Schema)}} instance for the extended {{term(schema)}}.   {{termplural(element name)}} identified with an "`x`" prefix are associated with this specific {{term(XML Schema)}} instance.
     *
     * > Note: The "`x`" prefix **MAY** be replaced with any prefix that the implementer chooses for identifying the extended {{term(schema)}} and {{term(namespace)}}.
     *
     * * `xsi:schemaLocation` is modified in Line 7 to associate the {{term(namespace)}} URN with the URL specifying the location of {{term(schema)}} file.
     *
     * * `MyLocation`, `MyFile`, `MyVersion`, and `MyFileName` in Lines 6 and 7 **MUST** be replaced by the actual name, version, and location of the extended {{term(schema)}}.
     *
     * When an extended {{term(schema)}} is implemented, each {{term(structural element)}}, {{term(DataItem)}}, and {{term(asset)}} defined in the extended {{term(schema)}} **MUST** be identified in each respective {{term(response document)}} by adding a prefix to the XML {{term(element name)}} associated with that {{term(structural element)}}, {{term(DataItem)}}, or {{term(asset)}}.  The prefix identifies the {{term(schema)}} and {{term(namespace)}} where that XML Element is defined. 
     */
}
package 'Observation Information Model' {
    connection def Conditions {
        end organizesCondition : Condition => organizedByComponentStream.organizesCondition;
        end organizedByComponentStream : 'Observation Information Model'::ComponentStream => organizesCondition.'Observation Information Model'::Condition::organizedByComponentStream;
        doc 
        /* {{block(Conditions)}} groups one or more {{block(Condition)}} entities. See {{sect(Condition)}}.
         *
         * > Note: In the {{term(XML)}} representation, {{block(Conditions)}} **MUST** appear as `Condition` element in the {{term(MTConnectStreams Response Document)}}.*/
    }
    connection def Entry {
        end result :>> Observation::result : Representations::Entry => isEntryFor.result;
        end isEntryFor : Representations::DataSet => result.'Observation Information Model'::Representations::Entry::isEntryFor;
        doc /* See {{sect(Entry)}}.*/
    }
    connection def Events {
        end organizesEvent : Event => organizedByComponentStream.organizesEvent;
        end organizedByComponentStream : 'Observation Information Model'::ComponentStream => organizesEvent.'Observation Information Model'::Event::organizedByComponentStream;
        doc /* {{block(Events)}} groups one or more {{block(Event)}} entities. See {{sect(Event)}}.*/
    }
    connection def Samples {
        end organizesSample : Sample => organizedByComponentStream.organizesSample;
        end organizedByComponentStream : 'Observation Information Model'::ComponentStream => organizesSample.'Observation Information Model'::Sample::organizedByComponentStream;
        doc /* {{block(Samples)}} groups one or more {{block(Sample)}} entities. See {{sect(Sample)}}.*/
    }
    connection def Observations {
        end madeByComponent : 'Device Information Model'::Components::Component => madeObservation.'Observation Information Model'::Observation::madeByComponent;
        end madeObservation : Observation => madeByComponent.madeObservation;
        doc 
        /* {{block(Observations)}} groups one or more {{block(Observation)}}s made by the {{block(Component)}} entity. 
         *
         * {{block(Component)}} make {{block(Observation)}}s about observed {{block(DataItem)}}s.
         *
         * See {{package(Observation Information Model)}} for the {{block(Observation)}} model.
         *
         * > Note 1 to entry: In the {{term(XML)}} representation, {{block(Observation)}} entities **MUST NOT** appear in the {{term(MTConnectDevices Response Document)}}.
         *
         * > Note 2 to entry: In the {{term(XML)}} representation, {{block(Observation)}} entities **MUST** appear only in the {{term(MTConnectStreams Response Document)}}.*/
    }
    package Representations {
        abstract part def Representation {
            doc /* specifies the format and structure of {{property(Observation::result)}}.*/
            comment /* Description*/
            doc 
            /* The {{block(Representation)}} type for an {{block(Observation)}} is defined by the associated {{property(DataItem::representation)}} in the {{term(MTConnectDevices Response Document)}}.
             *
             * {{block(Value)}} is the default {{block(Representation)}} type for all {{block(Observation)}} types.
             *
             * The name of the {{block(Observation)}} type is modified for all {{block(Representation)}} types other than {{block(Value)}} by appending the pascal case of the {{block(Representation)}} type. 
             *
             * Example: The name for {{block(Sample)}} {{block(Observation)}} type `Temperature`with `Representation` type of `TimeSeries` becomes `TemperatureTimeSeries`.*/
        }
        part def Value :> Representation {
            doc /* default {{block(Representation)}} type for all {{block(Observation)}} types where {{property(Observation::result)}} type is an MTConnect data type. See {{package(DataTypes)}}.*/
            attribute result [0..1] :>> Observation::result;
        }
        part def TimeSeries :> Representation {
            doc /* {{block(Representation)}} for an {{block(Observation)}} composed of a series of sampled data.
             */
            comment /* Description*/
            attribute sampleCount [1] : Profile::DataTypes::integer {
                doc /* number of values given for the {{block(Observation)}}.*/
            }
            attribute result [1..*] :>> Observation::result : Profile::DataTypes::float;
            doc 
            /*
             * {{block(TimeSeries)}} for an {{block(Observation)}} is defined by the associated {{property(DataItem::representation)}} as `TIME_SERIES`.
             *
             * {{property(DataItem::representation)}} as `TIME_SERIES` **MUST** have {{property(DataItem::category)}} of `SAMPLE`.
             *
             * {{figure(TemperatureTimeSeries)}} shows the model for {{block(Temperature)}} ({{block(Sample)}} type) with a {{block(Representation)}} type of {{block(TimeSeries)}}. 
             *
             * ![TemperatureTimeSeries](figures/TemperatureTimeSeries.png "TemperatureTimeSeries"){: width="0.8"}
             *
             * > Note: See {{sect(Representation Schema Diagrams)}} for XML schema.
             *
             * {{block(TimeSeries)}} **MUST** report multiple values at fixed intervals in a single {{block(Observation)}}. At minimum, one of {{property(DataItem::sampleRate)}} or {{property(Sample::sampleRate)}} **MUST** be specified. When both are specified, the {{property(Sample::sampleRate)}} supersedes the {{property(DataItem::sampleRate)}}.
             *
             * {{property(Observation::timestamp)}} **MUST** be set to the time the last value was observed. The {{property(Sample::duration)}} **MAY** indicate the time interval from the first to the last value in the series.
             *
             * {{sect(Value Properties of TimeSeries)}} defines additional attributes for an {{block(Observation)}} with {{block(TimeSeries)}} {{block(Representation)}} type.*/
        }
        part def Discrete :> Representation {
            doc /* **DEPRECATED** {{block(Representation)}} for an {{block(Observation)}} where each discrete occurrence of the data may have the same value as the previous occurrence of the data.
             */
            comment /* Description*/
            attribute result [0..1] :>> Observation::result : Profile::DataTypes::string;
            doc 
            /*
             * {{block(Discrete)}} for an {{block(Observation)}} is defined by the associated {{property(DataItem::representation)}} as `DISCRETE`.
             *
             * {{property(DataItem::representation)}} as `DISCRETE` **MUST** have {{property(DataItem::category)}} as `EVENT`.
             *
             * *MTConnect Version 1.5* replaced {{property(DataItem::representation)}} as `DISCRETE` with {{property(DataItem::discrete)}}.
             *
             * Each occurrence of the {{block(Observation)}} **MAY** have the same value as the previous occurrence, and **MUST NOT** suppress duplicates.
             *
             * Examples of {{block(Discrete)}}: A `PartCount` reporting the completion of each part using a 1 to indicate completion of a single part, a `Message` that occurs each time a door opens. */
        }
        part def DataSet :> Representation {
            doc /* {{block(Representation)}} for an {{block(Observation)}} composed of value(s) represented as a set of {{termplural(key-value pair)}}.
             */
            comment /* Description*/
            attribute count [1] : Profile::DataTypes::integer {
                doc /* number of {{block(Entry)}} elements for the {{block(Observation)}}.*/
            }
            part result [0..*] :>> Observation::result : Entry;
            doc 
            /*
             * {{block(DataSet)}} for an {{block(Observation)}} is defined by the associated {{property(DataItem::representation)}} as `DATA_SET`.
             *
             * {{property(DataItem::representation)}} as `DATA_SET` **MUST** have {{property(DataItem::category)}} as `SAMPLE` or `EVENT`.
             *
             * {{figure(VariableDataSet)}} shows the model for {{block(Variable)}} ({{block(Event)}} type) with a {{block(Representation)}} type of {{block(DataSet)}}. 
             *
             * ![VariableDataSet](figures/VariableDataSet.png "VariableDataSet"){: width="0.8"}
             *
             * > Note: See {{figure(DataSet Schema)}} for XML schema.
             *
             * {{block(DataSet)}} reports multiple values as a set of {{term(key-value pair)}} where each {{term(key)}} **MUST** be unique. The representation of the {{term(key-value pair)}} is an {{block(Entry)}}. The value of each {{block(Entry)}} **MUST** have the same constraints and format as the {{block(Observation)}} defined for {{property(DataItem::representation)}} as `VALUE` for the {{block(DataItem)}} type. (See {{block(Value)}}). 
             *
             * The meaning of each {{block(Entry)}} **MAY** be provided as the {{block(DataItem)}} {{block(EntryDefinition)}}.
             *
             * {{figure(DataSet Example)}} shows {{block(Event)}} {{block(Observation)}} type {{block(Variable)}} with a {{block(Representation)}} type of `DataSet`.
             *
             * ![DataSet Example](figures/DataSet%20Example.png "DataSet Example"){: width="0.8"}
             *
             * > Note: See {{lst(dataset-example)}} for the {{term(XML)}} representation of the same example.
             *
             * #### Management of Data Set Observations
             *
             * An {{term(agent)}} **MUST** maintain the current state of the {{block(DataSet)}} as described in {{package(Fundamentals)}}.
             *
             * One or more {{termplural(key-value pair)}} **MAY** be added, removed, or changed in an {{block(Observation)}}. An {{term(agent)}} **MUST** publish the changes to one or more {{termplural(key-value pair)}} as a single {{block(Observation)}}. An {{term(agent)}} **MUST** indicate the removal of a {{term(key-value pair)}} from a {{block(DataSet)}} using the {{property(Entry::removed)}} as `true`.
             *
             * When the {{property(DataItem::discrete)}} is `false` or is not present, an {{term(agent)}} in response to a {{term(sample request)}} **MUST** only publish the changed {{term(key-value pair)}} since the previous state of the {{block(DataSet)}}.
             *
             * When the {{property(DataItem::discrete)}} attribute is `true`, an {{term(agent)}}, in response to a {{term(sample request)}}, **MUST** report all {{termplural(key-value pair)}} ignoring the state of the {{block(DataSet)}}.
             *
             * When an {{term(agent)}} responds to a {{term(current request)}}, the {{term(response document)}} **MUST** include the full set of {{termplural(key-value pair)}}. If the {{term(current request)}} includes an `at` query parameter, the {{term(agent)}} **MUST** provide the set of {{termplural(key-value pair)}} at the  {{term(sequence number)}}.
             *
             * When an {{block(Observation)}} {{term(reset)}} occurs, the {{block(DataSet)}} **MUST** remove all {{termplural(key-value pair)}} making the set empty. The {{block(Observation)}} **MAY** simultaneously populate the {{block(DataSet)}} with new {{termplural(key-value pair)}}. The previous entries **MUST NOT** be included and **MUST NOT** have {{property(Entry::removed)}} as `true`.
             *
             * When the {{block(Observation)}}  is `UNAVAILABLE` the {{block(DataSet)}} **MUST** remove all {{termplural(key-value pair)}} making the set empty.*/
        }
        part def Entry {
            doc /* {{term(key-value pair)}} published as part of a {{block(DataSet)}}.*/
            comment /* Constraints for Entry Values*/
            attribute key [1] : Profile::DataTypes::ID {
                doc /* unique identifier for each {{term(key-value pair)}}.*/
            }
            attribute removed [0..1] : Profile::DataTypes::boolean {
                doc /* removal indicator of a {{term(key-value pair)}}.*/
            }
            private ref part isEntryFor [1] : DataSet;
            attribute result [0..1] : Profile::DataTypes::string {
                doc /* value of the {{block(Entry)}}.*/
            }
            doc 
            /*
             * The value of each {{block(Entry)}} **MUST** have the same restrictions as the value of an {{term(observation)}} with {{property(DataItem::representation)}} as `VALUE`.
             *
             * An {{block(Entry)}} **MAY** be further constrained by the {{block(DataItem)}} definition (see {{package(Device Information Model)}}), for example a `VariableDataSet` having a string value **MAY** have a floating-point {{block(Temperature)}} value. A restriction **MUST NOT** be broadened or removed, for example, the value "READY" **MUST NOT** occur with a `TemperatureDataSet` constrained to floating-point numbers.
             *
             * {{block(EntryDefinition)}} **MAY** provide the type and units of an {{property(Entry::key)}}.
             */
        }
        package Table {
            part def Table :> Representation {
                doc /* {{block(Representation)}} for an {{block(Observation)}} composed of two-dimensional sets of {{termplural(key-value pair)}} where the {{block(Entry)}} represents rows containing sets of {{termplural(key-value pair)}} given by {{block(Cell)}} entities. 
                 */
                comment /* Description*/
                part result [0..*] :>> Observation::result : 'Observation Information Model'::Representations::Table::Entry;
                attribute count [1] : Profile::DataTypes::integer {
                    doc /* number of {{termplural(key-value pair)}} represented as {{block(Entry)}} entities.*/
                }
                doc 
                /* {{block(Table)}} for an {{block(Observation)}} is defined by the associated {{property(DataItem::representation)}} as `TABLE`.
                 *
                 * {{property(DataItem::representation)}} as `TABLE` **MUST** have {{property(DataItem::category)}} as `SAMPLE` or `EVENT`.
                 *
                 * {{figure(WorkOffsetTable)}} shows the model for {{block(WorkOffset)}} ({{block(Event)}} type) with a {{block(Representation)}} type of {{block(Table)}}. 
                 *
                 * ![WorkOffsetTable](figures/WorkOffsetTable.png "WorkOffsetTable"){: width="0.8"}
                 *
                 * > Note: See {{sect(Representation Schema Diagrams)}} for XML schema.
                 *
                 * {{block(Table)}} has the same behavior as the {{block(DataSet)}} for change tracking, clearing, and history. When an {{block(Entry)}} changes, all {{block(Cell)}} entities update at the same time; they are not tracked separately like {{block(Entry)}}.
                 *
                 * The meaning of each {{block(Entry)}} and {{block(Cell)}} **MAY** be provided as the {{block(DataItem)}} {{block(EntryDefinition)}} and {{block(CellDefinition)}}.
                 *
                 * {{property(Entry::key)}}  **MUST** be the unique identity of the {{block(Entry)}} within an {{block(Observation)}}. {{property(Cell::key)}} **MUST** be the unique identity of the {{block(Cell)}} within an {{block(Entry)}}.
                 *
                 * {{figure(Table Example)}} shows {{block(Event)}} {{block(Observation)}} type {{block(WorkOffset)}} with a {{block(Representation)}} type of `Table`.
                 *
                 * ![Table Example](figures/Table%20Example.png "Table Example"){: width="0.8"}
                 *
                 * > Note: See {{lst(table-example)}} for the {{term(XML)}} representation of the same example.
                 *
                 */
            }
            connection def Entry {
                end result :>> Observation::result : 'Observation Information Model'::Representations::Table::Entry => isEntryFor.result;
                doc /* See {{sect(TableEntry)}}.*/
                private end isEntryFor : Representations::Table::Table;
            }
            part def Entry {
                doc 
                /* {{term(key-value pair)}} published as part of a {{block(Table)}}.
                 *
                 */
                attribute key [1] : Profile::DataTypes::ID {
                    doc /* unique identifier for each {{term(key-value pair)}}.*/
                }
                attribute removed [0..1] : Profile::DataTypes::boolean {
                    doc /* removal indicator of a {{term(key-value pair)}}.*/
                }
                part result [0..*] : Cell;
            }
            part def Cell {
                doc /* {{term(key-value pair)}} published as part of a {{block(TableEntry)}}.*/
                comment /* Constraints for Cell Values*/
                attribute key [1] : Profile::DataTypes::ID {
                    doc /* unique identifier for each {{term(key-value pair)}}.*/
                }
                attribute result [0..1] : Profile::DataTypes::string {
                    doc /* value of the {{block(Cell)}}.*/
                }
                doc 
                /* #### Constraints for Cell Values
                 *
                 * The value of each {{block(Cell)}} **MUST** have the same restrictions as the value of an {{term(observation)}} with {{property(DataItem::representation)}} as `VALUE`.
                 *
                 * An {{block(Cell)}} **MAY** be further constrained by the {{block(DataItem)}} definition (see {{package(Device Information Model)}}), for example a `VariableDataSet` having a string value **MAY** have a floating-point {{block(Temperature)}} value. A restriction **MUST NOT** be broadened or removed, for example, the value `READY` **MUST NOT** occur with a `TemperatureDataSet` constrained limited to floating-point numbers.
                 *
                 * {{block(CellDefinition)}} **MAY** provide type and units of a {{property(Cell::key)}}.*/
            }
            connection def Cell {
                end result : Cell => target.result;
                doc /* See {{sect(Cell)}}.*/
                private end : 'Observation Information Model'::Representations::Table::Entry;
            }
            doc /* This section provides semantic information for the {{block(Representation)}} type {{block(Table)}}.*/
        }
        doc 
        /* This section provides semantic information for the {{block(Representation)}} model.
         *
         * ![Representation](figures/Representation.png "Representation"){: width="0.8"}
         *
         * > Note: See {{sect(Representation Schema Diagrams)}} for XML schema.*/
    }
    package 'Observation Types' {
        package 'Sample Types' {
            part def Acceleration :> Sample {
                doc /* {{def(SampleEnum::ACCELERATION)}}*/
                constant attribute units :>> AccumulatedTime::units : Profile::DataTypes::UnitEnum :> AccumulatedTime::units default units::'MILLIMETER/SECOND^2';
                constant attribute type :>> type : Profile::DataTypes::SampleEnum :> type default type::ACCELERATION;
                constant attribute subType :>> subType : Profile::DataTypes::DataItemSubTypeEnum :> subType default subType::ACTUAL;
            }
            part def AccumulatedTime :> Sample {
                doc /* {{def(SampleEnum::ACCUMULATED_TIME)}}*/
                constant attribute units :>> Acceleration::units : Profile::DataTypes::UnitEnum :> Acceleration::units default units::SECOND;
                constant attribute type :>> Acceleration::type : Profile::DataTypes::SampleEnum :> Acceleration::type default type::ACCUMULATED_TIME;
            }
            part def Amperage :> Sample {
                doc /* {{def(SampleEnum::AMPERAGE)}}*/
                constant attribute units :>> Acceleration::units : Profile::DataTypes::UnitEnum :> Acceleration::units default "AMPERE";
                constant attribute type :>> type : Profile::DataTypes::SampleEnum :> type default type::AMPERAGE;
            }
            part def 'Amperage.Alternating' :> Amperage {
                doc 
                /* measurement of alternating voltage or current. 
                 *
                 * If not specified further in statistic, defaults to RMS voltage. 
                 *
                 * **DEPRECATED** in *Version 1.6*.*/
                constant attribute subType :>> subType : Profile::DataTypes::DataItemSubTypeEnum :> subType default "ALTERNATING";
            }
            part def 'Amperage.Direct' :> Amperage {
                doc 
                /* measurement of DC current or voltage.
                 *
                 * **DEPRECATED** in *Version 1.6*.*/
                constant attribute subType :>> subType : Profile::DataTypes::DataItemSubTypeEnum :> subType default "DIRECT";
            }
            part def 'Amperage.Actual' :> Amperage {
                doc 
                /* measured or reported value of an {{term(observation)}}.
                 *
                 * **DEPRECATED** in *Version 1.6*.*/
                constant attribute subType :>> subType : Profile::DataTypes::DataItemSubTypeEnum :> subType default "ACTUAL";
            }
            part def 'Amperage.Target' :> Amperage {
                doc 
                /* goal of the operation or process.
                 *
                 * **DEPRECATED** in *Version 1.6*.*/
                constant attribute subType :>> subType : Profile::DataTypes::DataItemSubTypeEnum :> subType default "TARGET";
            }
            part def Angle :> Sample {
                doc /* {{def(SampleEnum::ANGLE)}}*/
                constant attribute units :>> Acceleration::units : Profile::DataTypes::UnitEnum :> Acceleration::units default units::DEGREE;
                constant attribute type :>> type : Profile::DataTypes::SampleEnum :> Acceleration::type default type::ANGLE;
            }
            part def 'Angle.Commanded' :> Angle {
                doc /* directive value including adjustments such as an offset or overrides.*/
                constant attribute subType :>> subType : Profile::DataTypes::DataItemSubTypeEnum :> subType default "COMMANDED";
            }
            part def 'Angle.Actual' :> Angle {
                doc /* measured or reported value of an {{term(observation)}}.*/
                constant attribute subType :>> subType : Profile::DataTypes::DataItemSubTypeEnum :> subType default "ACTUAL";
            }
            part def AngularAcceleration :> Sample {
                doc /* {{def(SampleEnum::ANGULAR_ACCELERATION)}}*/
                constant attribute units :>> Acceleration::units : Profile::DataTypes::UnitEnum :> Acceleration::units default units::'DEGREE/SECOND^2';
                constant attribute type :>> type : Profile::DataTypes::SampleEnum :> Acceleration::type default type::ANGULAR_ACCELERATION;
                constant attribute subType :>> subType : Profile::DataTypes::DataItemSubTypeEnum :> subType default subType::ACTUAL;
            }
            part def AngularVelocity :> Sample {
                doc /* {{def(SampleEnum::ANGULAR_VELOCITY)}}*/
                constant attribute units :>> Acceleration::units : Profile::DataTypes::UnitEnum :> Acceleration::units default units::'DEGREE/SECOND';
                constant attribute type :>> type : Profile::DataTypes::SampleEnum :> Acceleration::type default type::ANGULAR_VELOCITY;
            }
            part def AxisFeedrate :> Sample {
                doc /* {{def(SampleEnum::AXIS_FEEDRATE)}}*/
                constant attribute units :>> Acceleration::units : Profile::DataTypes::UnitEnum :> Acceleration::units default units::'MILLIMETER/SECOND';
                constant attribute type :>> type : Profile::DataTypes::SampleEnum :> Acceleration::type default type::AXIS_FEEDRATE;
            }
            part def 'AxisFeedrate.Actual' :> AxisFeedrate {
                doc /* measured or reported value of an {{term(observation)}}.*/
                constant attribute subType :>> subType : Profile::DataTypes::DataItemSubTypeEnum :> subType default "ACTUAL";
            }
            part def 'AxisFeedrate.Commanded' :> AxisFeedrate {
                doc /* directive value including adjustments such as an offset or overrides.*/
                constant attribute subType :>> subType : Profile::DataTypes::DataItemSubTypeEnum :> subType default "COMMANDED";
            }
            part def 'AxisFeedrate.Jog' :> AxisFeedrate {
                doc 
                /* relating to momentary activation of a function or a movement.
                 *
                 * **DEPRECATION WARNING**: May be deprecated in the future.*/
                constant attribute subType :>> subType : Profile::DataTypes::DataItemSubTypeEnum :> subType default "JOG";
            }
            part def 'AxisFeedrate.Programmed' :> AxisFeedrate {
                doc /* directive value without offsets and adjustments.*/
                constant attribute subType :>> subType : Profile::DataTypes::DataItemSubTypeEnum :> subType default "PROGRAMMED";
            }
            part def 'AxisFeedrate.Rapid' :> AxisFeedrate {
                doc /* performing an operation faster or in less time than nominal rate.*/
                constant attribute subType :>> subType : Profile::DataTypes::DataItemSubTypeEnum :> subType default "RAPID";
            }
            part def 'AxisFeedrate.Override' :> AxisFeedrate {
                doc /* operator's overridden value.*/
                constant attribute subType :>> subType : Profile::DataTypes::DataItemSubTypeEnum :> subType default "OVERRIDE";
            }
            part def CapacityFluid :> Sample {
                doc /* {{def(SampleEnum::CAPACITY_FLUID)}}*/
                constant attribute units :>> Acceleration::units : Profile::DataTypes::UnitEnum :> Acceleration::units default units::MILLILITER;
                constant attribute type :>> type : Profile::DataTypes::SampleEnum :> Acceleration::type default type::CAPACITY_FLUID;
            }
            part def CapacitySpatial :> Sample {
                doc /* {{def(SampleEnum::CAPACITY_SPATIAL)}}*/
                constant attribute units :>> Acceleration::units : Profile::DataTypes::UnitEnum :> Acceleration::units default units::CUBIC_MILLIMETER;
                constant attribute type :>> type : Profile::DataTypes::SampleEnum :> Acceleration::type default type::CAPACITY_SPATIAL;
            }
            part def Concentration :> Sample {
                doc /* {{def(SampleEnum::CONCENTRATION)}}*/
                constant attribute units :>> Acceleration::units : Profile::DataTypes::UnitEnum :> Acceleration::units default units::PERCENT;
                constant attribute type :>> type : Profile::DataTypes::SampleEnum :> Acceleration::type default type::CONCENTRATION;
            }
            part def Conductivity :> Sample {
                doc /* {{def(SampleEnum::CONDUCTIVITY)}}*/
                constant attribute units :>> Acceleration::units : Profile::DataTypes::UnitEnum :> Acceleration::units default units::'SIEMENS/METER';
                constant attribute type :>> type : Profile::DataTypes::SampleEnum :> Acceleration::type default type::CONDUCTIVITY;
            }
            part def CuttingSpeed :> Sample {
                doc /* {{def(SampleEnum::CUTTING_SPEED)}}*/
                constant attribute units :>> Acceleration::units : Profile::DataTypes::UnitEnum :> Acceleration::units default units::'MILLIMETER/SECOND';
                constant attribute type :>> type : Profile::DataTypes::SampleEnum :> Acceleration::type default type::CUTTING_SPEED;
            }
            part def 'CuttingSpeed.Actual' :> CuttingSpeed {
                doc /* measured or reported value of an {{term(observation)}}.*/
                constant attribute subType :>> subType : Profile::DataTypes::DataItemSubTypeEnum :> subType default "ACTUAL";
            }
            part def 'CuttingSpeed.Commanded' :> CuttingSpeed {
                doc /* directive value including adjustments such as an offset or overrides.*/
                constant attribute subType :>> subType : Profile::DataTypes::DataItemSubTypeEnum :> subType default "COMMANDED";
            }
            part def 'CuttingSpeed.Programmed' :> CuttingSpeed {
                doc /* directive value without offsets and adjustments.*/
                constant attribute subType :>> subType : Profile::DataTypes::DataItemSubTypeEnum :> subType default "PROGRAMMED";
            }
            part def Density :> Sample {
                doc /* {{def(SampleEnum::DENSITY)}}*/
                constant attribute units :>> Acceleration::units : Profile::DataTypes::UnitEnum :> Acceleration::units default units::'MILLIGRAM/CUBIC_MILLIMETER';
                constant attribute type :>> type : Profile::DataTypes::SampleEnum :> Acceleration::type default type::DENSITY;
            }
            part def DepositionAccelerationVolumetric :> Sample {
                doc /* {{def(SampleEnum::DEPOSITION_ACCELERATION_VOLUMETRIC)}}*/
                constant attribute units :>> Acceleration::units : Profile::DataTypes::UnitEnum :> Acceleration::units default units::'CUBIC_MILLIMETER/SECOND^2';
                constant attribute type :>> Acceleration::type : Profile::DataTypes::SampleEnum :> Acceleration::type default type::DEPOSITION_ACCELERATION_VOLUMETRIC;
            }
            part def 'DepositionAccelerationVolumetric.Actual' :> DepositionAccelerationVolumetric {
                doc /* measured or reported value of an {{term(observation)}}.*/
                constant attribute subType :>> subType : Profile::DataTypes::DataItemSubTypeEnum :> subType default "ACTUAL";
            }
            part def 'DepositionAccelerationVolumetric.Commanded' :> DepositionAccelerationVolumetric {
                doc /* directive value including adjustments such as an offset or overrides.*/
                constant attribute subType :>> subType : Profile::DataTypes::DataItemSubTypeEnum :> subType default "COMMANDED";
            }
            part def DepositionDensity :> Sample {
                doc /* {{def(SampleEnum::DEPOSITION_DENSITY)}}*/
                constant attribute units :>> Acceleration::units : Profile::DataTypes::UnitEnum :> Acceleration::units default units::'MILLIGRAM/CUBIC_MILLIMETER';
                constant attribute type :>> type : Profile::DataTypes::SampleEnum :> Acceleration::type default type::DEPOSITION_DENSITY;
            }
            part def 'DepositionDensity.Actual' :> DepositionDensity {
                doc /* measured or reported value of an {{term(observation)}}.*/
                constant attribute subType :>> subType : Profile::DataTypes::DataItemSubTypeEnum :> subType default "ACTUAL";
            }
            part def 'DepositionDensity.Commanded' :> DepositionDensity {
                doc /* directive value including adjustments such as an offset or overrides.*/
                constant attribute subType :>> subType : Profile::DataTypes::DataItemSubTypeEnum :> subType default "COMMANDED";
            }
            part def DepositionMass :> Sample {
                doc /* {{def(SampleEnum::DEPOSITION_MASS)}}*/
                constant attribute units :>> Acceleration::units : Profile::DataTypes::UnitEnum :> Acceleration::units default units::MILLIGRAM;
                constant attribute type :>> type : Profile::DataTypes::SampleEnum :> Acceleration::type default type::DEPOSITION_MASS;
            }
            part def 'DepositionMass.Actual' :> DepositionMass {
                doc /* measured or reported value of an {{term(observation)}}.*/
                constant attribute subType :>> subType : Profile::DataTypes::DataItemSubTypeEnum :> subType default "ACTUAL";
            }
            part def 'DepositionMass.Commanded' :> DepositionMass {
                doc /* directive value including adjustments such as an offset or overrides.*/
                constant attribute subType :>> subType : Profile::DataTypes::DataItemSubTypeEnum :> subType default "COMMANDED";
            }
            part def DepositionRateVolumetric :> Sample {
                doc /* {{def(SampleEnum::DEPOSITION_RATE_VOLUMETRIC)}}*/
                constant attribute units :>> Acceleration::units : Profile::DataTypes::UnitEnum :> Acceleration::units default units::'CUBIC_MILLIMETER/SECOND';
                constant attribute type :>> type : Profile::DataTypes::SampleEnum :> Acceleration::type default type::DEPOSITION_RATE_VOLUMETRIC;
            }
            part def 'DepositionRateVolumetric.Actual' :> DepositionRateVolumetric {
                doc /* measured or reported value of an {{term(observation)}}.*/
                constant attribute subType :>> subType : Profile::DataTypes::DataItemSubTypeEnum :> subType default "ACTUAL";
            }
            part def 'DepositionRateVolumetric.Commanded' :> DepositionRateVolumetric {
                doc /* directive value including adjustments such as an offset or overrides.*/
                constant attribute subType :>> subType : Profile::DataTypes::DataItemSubTypeEnum :> subType default "COMMANDED";
            }
            part def DepositionVolume :> Sample {
                doc /* {{def(SampleEnum::DEPOSITION_VOLUME)}}*/
                constant attribute units :>> Acceleration::units : Profile::DataTypes::UnitEnum :> Acceleration::units default units::CUBIC_MILLIMETER;
                constant attribute type :>> type : Profile::DataTypes::SampleEnum :> Acceleration::type default type::DEPOSITION_VOLUME;
            }
            part def 'DepositionVolume.Actual' :> DepositionVolume {
                doc /* measured or reported value of an {{term(observation)}}.*/
                constant attribute subType :>> subType : Profile::DataTypes::DataItemSubTypeEnum :> subType default "ACTUAL";
            }
            part def 'DepositionVolume.Commanded' :> DepositionVolume {
                doc /* directive value including adjustments such as an offset or overrides.*/
                constant attribute subType :>> subType : Profile::DataTypes::DataItemSubTypeEnum :> subType default "COMMANDED";
            }
            part def Displacement :> Sample {
                doc /* {{def(SampleEnum::DISPLACEMENT)}}*/
                constant attribute units :>> Acceleration::units : Profile::DataTypes::UnitEnum :> Acceleration::units default units::MILLIMETER;
                constant attribute type :>> type : Profile::DataTypes::SampleEnum :> Acceleration::type default type::DISPLACEMENT;
            }
            part def ElectricalEnergy :> Sample {
                doc /* {{def(SampleEnum::ELECTRICAL_ENERGY)}}*/
                constant attribute units :>> Acceleration::units : Profile::DataTypes::UnitEnum :> Acceleration::units default units::WATT_SECOND;
                constant attribute type :>> type : Profile::DataTypes::SampleEnum :> Acceleration::type default type::ELECTRICAL_ENERGY;
            }
            part def EquipmentTimer :> Sample {
                doc /* {{def(SampleEnum::EQUIPMENT_TIMER)}}*/
                constant attribute units :>> Acceleration::units : Profile::DataTypes::UnitEnum :> Acceleration::units default units::SECOND;
                constant attribute type :>> type : Profile::DataTypes::SampleEnum :> Acceleration::type default type::EQUIPMENT_TIMER;
                constant attribute subType [1] :>> subType : Profile::DataTypes::DataItemSubTypeEnum :> subType;
            }
            part def 'EquipmentTimer.Loaded' :> EquipmentTimer {
                doc 
                /* time that the sub-parts of a piece of equipment are under load.
                 *
                 * Example: For traditional machine tools, this is a measurement of the time that the cutting tool is assumed to be engaged with the part.*/
                constant attribute subType :>> Acceleration::subType : Profile::DataTypes::DataItemSubTypeEnum :> Acceleration::subType default "LOADED";
            }
            part def 'EquipmentTimer.Working' :> EquipmentTimer {
                doc 
                /* time that a piece of equipment is performing any activity the equipment is active and performing a function under load or not.
                 *
                 * Example: For traditional machine tools, this includes `LOADED`, plus rapid moves, tool changes, etc.*/
                constant attribute subType :>> Acceleration::subType : Profile::DataTypes::DataItemSubTypeEnum :> Acceleration::subType default "WORKING";
            }
            part def 'EquipmentTimer.Operating' :> EquipmentTimer {
                doc 
                /* time that the major sub-parts of a piece of equipment are powered or performing any activity whether producing a part or product or not.
                 *
                 * Example: For traditional machine tools, this includes `WORKING`, plus idle time.*/
                constant attribute subType :>> Acceleration::subType : Profile::DataTypes::DataItemSubTypeEnum :> Acceleration::subType default "OPERATING";
            }
            part def 'EquipmentTimer.Powered' :> EquipmentTimer {
                doc 
                /* time that primary power is applied to the piece of equipment and, as a minimum, the controller or logic portion of the piece of equipment is powered and functioning or components that are required to remain on are powered.
                 *
                 * Example: Heaters for an extrusion machine that are required to be powered even when the equipment is turned off.*/
                constant attribute subType :>> Acceleration::subType : Profile::DataTypes::DataItemSubTypeEnum :> Acceleration::subType default "POWERED";
            }
            part def 'EquipmentTimer.Delay' :> EquipmentTimer {
                doc /* elapsed time of a temporary halt of action.*/
                constant attribute subType :>> Acceleration::subType : Profile::DataTypes::DataItemSubTypeEnum :> Acceleration::subType default "DELAY";
            }
            part def FillLevel :> Sample {
                doc /* {{def(SampleEnum::FILL_LEVEL)}}*/
                constant attribute units :>> Acceleration::units : Profile::DataTypes::UnitEnum :> Acceleration::units default units::PERCENT;
                constant attribute type :>> type : Profile::DataTypes::SampleEnum :> Acceleration::type default type::FILL_LEVEL;
            }
            part def Flow :> Sample {
                doc /* {{def(SampleEnum::FLOW)}}*/
                constant attribute units :>> Acceleration::units : Profile::DataTypes::UnitEnum :> Acceleration::units default units::'LITER/SECOND';
                constant attribute type :>> type : Profile::DataTypes::SampleEnum :> Acceleration::type default type::FLOW;
            }
            part def Frequency :> Sample {
                doc /* {{def(SampleEnum::FREQUENCY)}}*/
                constant attribute units :>> Acceleration::units : Profile::DataTypes::UnitEnum :> Acceleration::units default units::HERTZ;
                constant attribute type :>> type : Profile::DataTypes::SampleEnum :> Acceleration::type default type::FREQUENCY;
            }
            part def GlobalPosition :> Sample {
                doc /* {{def(SampleEnum::GLOBAL_POSITION)}}*/
                constant attribute type :>> type : Profile::DataTypes::SampleEnum :> Acceleration::type default type::GLOBAL_POSITION;
                constant attribute units :>> Acceleration::units : Profile::DataTypes::UnitEnum :> Acceleration::units default units::MILLIMETER;
            }
            part def Length :> Sample {
                doc /* {{def(SampleEnum::LENGTH)}}*/
                constant attribute units :>> Acceleration::units : Profile::DataTypes::UnitEnum :> Acceleration::units default units::MILLIMETER;
                constant attribute type :>> type : Profile::DataTypes::SampleEnum :> Acceleration::type default type::LENGTH;
            }
            part def 'Length.Standard' :> Length {
                doc /* standard or original length of an object.*/
                constant attribute subType :>> subType : Profile::DataTypes::DataItemSubTypeEnum :> subType default "STANDARD";
            }
            part def 'Length.Remaining' :> Length {
                doc /* remaining total length of an object.*/
                constant attribute subType :>> subType : Profile::DataTypes::DataItemSubTypeEnum :> subType default "REMAINING";
            }
            part def 'Length.Useable' :> Length {
                doc /* remaining usable length of an object.*/
                constant attribute subType :>> subType : Profile::DataTypes::DataItemSubTypeEnum :> subType default "USEABLE";
            }
            part def Level :> Sample {
                doc /* {{def(SampleEnum::LEVEL)}}*/
                constant attribute type :>> type : Profile::DataTypes::SampleEnum :> Acceleration::type default type::LEVEL;
                constant attribute units :>> Acceleration::units : Profile::DataTypes::UnitEnum :> Acceleration::units default "PERCENT";
            }
            part def LinearForce :> Sample {
                doc /* {{def(SampleEnum::LINEAR_FORCE)}}*/
                constant attribute units :>> Acceleration::units : Profile::DataTypes::UnitEnum :> Acceleration::units default units::NEWTON;
                constant attribute type :>> type : Profile::DataTypes::SampleEnum :> Acceleration::type default type::LINEAR_FORCE;
            }
            part def Load :> Sample {
                doc /* {{def(SampleEnum::LOAD)}}*/
                constant attribute units :>> Acceleration::units : Profile::DataTypes::UnitEnum :> Acceleration::units default units::PERCENT;
                constant attribute type :>> type : Profile::DataTypes::SampleEnum :> Acceleration::type default type::LOAD;
            }
            part def Mass :> Sample {
                doc /* {{def(SampleEnum::MASS)}}*/
                constant attribute units :>> Acceleration::units : Profile::DataTypes::UnitEnum :> Acceleration::units default units::KILOGRAM;
                constant attribute type :>> type : Profile::DataTypes::SampleEnum :> Acceleration::type default type::MASS;
            }
            part def PathFeedrate :> Sample {
                doc /* {{def(SampleEnum::PATH_FEEDRATE)}}*/
                constant attribute units :>> Acceleration::units : Profile::DataTypes::UnitEnum :> Acceleration::units default units::'MILLIMETER/SECOND';
                constant attribute type :>> type : Profile::DataTypes::SampleEnum :> Acceleration::type default type::PATH_FEEDRATE;
            }
            part def 'PathFeedrate.Actual' :> PathFeedrate {
                doc /* measured or reported value of an {{term(observation)}}.*/
                constant attribute subType :>> subType : Profile::DataTypes::DataItemSubTypeEnum :> subType default "ACTUAL";
            }
            part def 'PathFeedrate.Commanded' :> PathFeedrate {
                doc /* directive value including adjustments such as an offset or overrides.*/
                constant attribute subType :>> subType : Profile::DataTypes::DataItemSubTypeEnum :> subType default "COMMANDED";
            }
            part def 'PathFeedrate.Jog' :> PathFeedrate {
                doc 
                /* relating to momentary activation of a function or a movement.
                 *
                 * **DEPRECATION WARNING**: May be deprecated in the future.*/
                constant attribute subType :>> subType : Profile::DataTypes::DataItemSubTypeEnum :> subType default "JOG";
            }
            part def 'PathFeedrate.Programmed' :> PathFeedrate {
                doc /* directive value without offsets and adjustments.*/
                constant attribute subType :>> subType : Profile::DataTypes::DataItemSubTypeEnum :> subType default "PROGRAMMED";
            }
            part def 'PathFeedrate.Rapid' :> PathFeedrate {
                doc /* performing an operation faster or in less time than nominal rate.*/
                constant attribute subType :>> subType : Profile::DataTypes::DataItemSubTypeEnum :> subType default "RAPID";
            }
            part def 'PathFeedrate.Override' :> PathFeedrate {
                doc 
                /* operator's overridden value.
                 *
                 * **DEPRECATED** in *Version 1.3*.*/
                constant attribute subType :>> subType : Profile::DataTypes::DataItemSubTypeEnum :> subType default "OVERRIDE";
            }
            part def PathFeedratePerRevolution :> Sample {
                doc /* {{def(SampleEnum::PATH_FEEDRATE_PER_REVOLUTION)}}*/
                constant attribute units :>> Acceleration::units : Profile::DataTypes::UnitEnum :> Acceleration::units default units::'MILLIMETER/REVOLUTION';
                constant attribute type :>> Acceleration::type : Profile::DataTypes::SampleEnum :> Acceleration::type default type::PATH_FEEDRATE_PER_REVOLUTION;
            }
            part def 'PathFeedratePerRevolution.Actual' :> PathFeedratePerRevolution {
                doc /* measured or reported value of an {{term(observation)}}.*/
                constant attribute subType :>> subType : Profile::DataTypes::DataItemSubTypeEnum :> subType default "ACTUAL";
            }
            part def 'PathFeedratePerRevolution.Commanded' :> PathFeedratePerRevolution {
                doc /* directive value including adjustments such as an offset or overrides.*/
                constant attribute subType :>> subType : Profile::DataTypes::DataItemSubTypeEnum :> subType default "COMMANDED";
            }
            part def 'PathFeedratePerRevolution.Programmed' :> PathFeedratePerRevolution {
                doc /* directive value without offsets and adjustments.*/
                constant attribute subType :>> subType : Profile::DataTypes::DataItemSubTypeEnum :> subType default "PROGRAMMED";
            }
            part def PathPosition :> Sample {
                doc 
                /* {{def(SampleEnum::PATH_POSITION)}}
                 *
                 */
                comment /* Example*/
                constant attribute units :>> Acceleration::units : Profile::DataTypes::UnitEnum :> Acceleration::units default units::MILLIMETER_3D;
                constant attribute type :>> type : Profile::DataTypes::SampleEnum :> Acceleration::type default type::PATH_POSITION;
                attribute result [0..1] :>> Acceleration::result : Profile::DataTypes::float3d;
                doc 
                /* ~~~~xml
                 * <DataItem type='PATH_POSITION' id='pathposit1' units="MILLIMETER_3D"/>
                 * ~~~~
                 * {: caption="XML Device Model Example for `PathPosition` using `MILLIMETER_3D` unit"}
                 *
                 * ~~~~xml
                 * <PathPosition>10.0 0.0 20.0</PathPosition>
                 * ~~~~
                 * {: caption="XML Streams Response Example for `PathPosition` using `MILLIMETER_3D` unit"}
                 *
                 *
                 * ~~~~xml
                 * <DataItem type='PATH_POSITION' id='pathposit1' representation="DATA_SET">
                 *   <Definition>
                 *     <EntryDefinition key='X' units='MILLIMETER'>
                 *     <EntryDefinition key='Y' units='MILLIMETER'>
                 *     <EntryDefinition key='Z' units='MILLIMETER'>
                 *   </Definition>
                 * </DataItem>
                 * ~~~~
                 * {: caption="XML Device Model Example for `PathPosition` to demonstrate multi-dimensional representation using `DataSet` representation"}
                 *
                 * ~~~~xml
                 * <PathPositionDataSet id='pathposit1'>
                 *   <Entry key='X'>10.0</Entry>
                 *   <Entry key='Z'>20.0</Entry>
                 * </PathPositionDataSet>
                 * ~~~~
                 * {: caption="XML Streams Response Example for `PathPosition` to demonstrate multi-dimensional representation using `DataSet` representation"}*/
            }
            part def 'PathPosition.Actual' :> PathPosition {
                doc /* measured or reported value of an {{term(observation)}}.*/
                constant attribute subType :>> subType : Profile::DataTypes::DataItemSubTypeEnum :> subType default "ACTUAL";
            }
            part def 'PathPosition.Commanded' :> PathPosition {
                doc /* directive value including adjustments such as an offset or overrides.*/
                constant attribute subType :>> subType : Profile::DataTypes::DataItemSubTypeEnum :> subType default "COMMANDED";
            }
            part def 'PathPosition.Target' :> PathPosition {
                doc /* goal of the operation or process.*/
                constant attribute subType :>> subType : Profile::DataTypes::DataItemSubTypeEnum :> subType default "TARGET";
            }
            part def 'PathPosition.Probe' :> PathPosition {
                doc 
                /* position provided by a measurement probe.
                 *
                 * **DEPRECATION WARNING**: May be deprecated in the future.*/
                constant attribute subType :>> subType : Profile::DataTypes::DataItemSubTypeEnum :> subType default "PROBE";
            }
            part def PH :> Sample {
                doc /* {{def(SampleEnum::PH)}}*/
                constant attribute units :>> Acceleration::units : Profile::DataTypes::UnitEnum :> Acceleration::units default units::PH;
                constant attribute type :>> type : Profile::DataTypes::SampleEnum :> Acceleration::type default type::PH;
            }
            part def Position :> Sample {
                doc /* {{def(SampleEnum::POSITION)}}*/
                constant attribute units :>> units : Profile::DataTypes::UnitEnum :> Acceleration::units default units::MILLIMETER;
                constant attribute type :>> type : Profile::DataTypes::SampleEnum :> Acceleration::type default type::POSITION;
            }
            part def 'Position.Actual' :> Position {
                doc /* measured or reported value of an {{term(observation)}}.*/
                constant attribute subType [1] :>> subType : Profile::DataTypes::DataItemSubTypeEnum :> subType default "ACTUAL";
            }
            part def 'Position.Commanded' :> Position {
                doc /* directive value including adjustments such as an offset or overrides.*/
                constant attribute subType :>> subType : Profile::DataTypes::DataItemSubTypeEnum :> subType default "COMMANDED";
            }
            part def 'Position.Programmed' :> Position {
                doc /* directive value without offsets and adjustments.*/
                constant attribute subType :>> subType : Profile::DataTypes::DataItemSubTypeEnum :> subType default "PROGRAMMED";
            }
            part def 'Position.Target' :> Position {
                doc /* goal of the operation or process.*/
                constant attribute subType :>> subType : Profile::DataTypes::DataItemSubTypeEnum :> subType default "TARGET";
            }
            part def PowerFactor :> Sample {
                doc /* {{def(SampleEnum::POWER_FACTOR)}}*/
                constant attribute units :>> Acceleration::units : Profile::DataTypes::UnitEnum :> Acceleration::units default units::PERCENT;
                constant attribute type :>> type : Profile::DataTypes::SampleEnum :> Acceleration::type default type::POWER_FACTOR;
            }
            part def Pressure :> Sample {
                doc /* {{def(SampleEnum::PRESSURE)}}*/
                constant attribute units :>> Acceleration::units : Profile::DataTypes::UnitEnum :> Acceleration::units default units::PASCAL;
                constant attribute type :>> type : Profile::DataTypes::SampleEnum :> Acceleration::type default type::PRESSURE;
            }
            part def ProcessTimer :> Sample {
                doc /* {{def(SampleEnum::PROCESS_TIMER)}}*/
                constant attribute units :>> Acceleration::units : Profile::DataTypes::UnitEnum :> Acceleration::units default units::SECOND;
                constant attribute type :>> type : Profile::DataTypes::SampleEnum :> Acceleration::type default type::PROCESS_TIMER;
                constant attribute subType [1] :>> subType : Profile::DataTypes::DataItemSubTypeEnum :> subType;
            }
            part def 'ProcessTimer.Process' :> ProcessTimer {
                doc 
                /* time from the beginning of production of a part or product on a piece of equipment until the time that production is complete for that part or product on
                 * that piece of equipment.
                 *
                 * This includes the time that the piece of equipment is running, producing parts or products, or in the process of producing parts.*/
                constant attribute subType :>> Acceleration::subType : Profile::DataTypes::DataItemSubTypeEnum :> Acceleration::subType default "PROCESS";
            }
            part def 'ProcessTimer.Delay' :> ProcessTimer {
                doc /* elapsed time of a temporary halt of action.*/
                constant attribute subType :>> Acceleration::subType : Profile::DataTypes::DataItemSubTypeEnum :> Acceleration::subType default "DELAY";
            }
            part def Resistance :> Sample {
                doc /* {{def(SampleEnum::RESISTANCE)}}*/
                constant attribute units :>> Acceleration::units : Profile::DataTypes::UnitEnum :> Acceleration::units default units::OHM;
                constant attribute type :>> type : Profile::DataTypes::SampleEnum :> Acceleration::type default type::RESISTANCE;
            }
            part def RotaryVelocity :> Sample {
                doc /* {{def(SampleEnum::ROTARY_VELOCITY)}}*/
                constant attribute units :>> Acceleration::units : Profile::DataTypes::UnitEnum :> Acceleration::units default units::'REVOLUTION/MINUTE';
                constant attribute type :>> type : Profile::DataTypes::SampleEnum :> Acceleration::type default type::ROTARY_VELOCITY;
            }
            part def 'RotaryVelocity.Actual' :> RotaryVelocity {
                doc /* measured or reported value of an {{term(observation)}}.*/
                constant attribute subType :>> subType : Profile::DataTypes::DataItemSubTypeEnum :> subType default "ACTUAL";
            }
            part def 'RotaryVelocity.Commanded' :> RotaryVelocity {
                doc /* directive value including adjustments such as an offset or overrides.*/
                constant attribute subType :>> subType : Profile::DataTypes::DataItemSubTypeEnum :> subType default "COMMANDED";
            }
            part def 'RotaryVelocity.Programmed' :> RotaryVelocity {
                doc /* directive value without offsets and adjustments.*/
                constant attribute subType :>> subType : Profile::DataTypes::DataItemSubTypeEnum :> subType default "PROGRAMMED";
            }
            part def 'RotaryVelocity.Override' :> RotaryVelocity {
                doc 
                /* The operators overridden value.
                 *
                 */
                constant attribute subType :>> subType : Profile::DataTypes::DataItemSubTypeEnum :> subType default "OVERRIDE";
            }
            part def SoundLevel :> Sample {
                doc /* {{def(SampleEnum::SOUND_LEVEL)}}*/
                constant attribute units :>> Acceleration::units : Profile::DataTypes::UnitEnum :> Acceleration::units default units::DECIBEL;
                constant attribute type :>> type : Profile::DataTypes::SampleEnum :> Acceleration::type default type::SOUND_LEVEL;
                constant attribute subType :>> subType : Profile::DataTypes::DataItemSubTypeEnum :> subType default subType::A_SCALE;
            }
            part def 'SoundLevel.NoScale' :> SoundLevel {
                doc /* No weighting factor on the frequency scale*/
                constant attribute subType :>> Acceleration::subType : Profile::DataTypes::DataItemSubTypeEnum :> Acceleration::subType default "NO_SCALE";
            }
            part def 'SoundLevel.AScale' :> SoundLevel {
                doc /* A Scale weighting factor.   This is the default weighting factor if no factor is specified*/
                constant attribute subType :>> Acceleration::subType : Profile::DataTypes::DataItemSubTypeEnum :> Acceleration::subType default "A_SCALE";
            }
            part def 'SoundLevel.BScale' :> SoundLevel {
                doc /* B Scale weighting factor*/
                constant attribute subType :>> Acceleration::subType : Profile::DataTypes::DataItemSubTypeEnum :> Acceleration::subType default "B_SCALE";
            }
            part def 'SoundLevel.CScale' :> SoundLevel {
                doc /* C Scale weighting factor*/
                constant attribute subType :>> Acceleration::subType : Profile::DataTypes::DataItemSubTypeEnum :> Acceleration::subType default "C_SCALE";
            }
            part def 'SoundLevel.DScale' :> SoundLevel {
                doc /* D Scale weighting factor*/
                constant attribute subType :>> Acceleration::subType : Profile::DataTypes::DataItemSubTypeEnum :> Acceleration::subType default "D_SCALE";
            }
            part def SpindleSpeed :> Sample {
                doc /* {{def(SampleEnum::SPINDLE_SPEED)}}*/
                constant attribute units :>> Acceleration::units : Profile::DataTypes::UnitEnum :> Acceleration::units default units::'REVOLUTION/MINUTE';
                constant attribute type :>> type : Profile::DataTypes::SampleEnum :> Acceleration::type default type::SPINDLE_SPEED;
            }
            part def 'SpindleSpeed.Actual' :> SpindleSpeed {
                doc 
                /* measured or reported value of an {{term(observation)}}.
                 *
                 * **DEPRECATED** in *Version 1.3*.*/
                constant attribute subType :>> subType : Profile::DataTypes::DataItemSubTypeEnum :> subType default "ACTUAL";
            }
            part def 'SpindleSpeed.Commanded' :> SpindleSpeed {
                doc 
                /* directive value including adjustments such as an offset or overrides.
                 *
                 * **DEPRECATED** in *Version 1.3*.*/
                constant attribute subType :>> subType : Profile::DataTypes::DataItemSubTypeEnum :> subType default "COMMANDED";
            }
            part def 'SpindleSpeed.Override' :> SpindleSpeed {
                doc 
                /* operator's overridden value.
                 *
                 * **DEPRECATED** in *Version 1.3*.*/
                constant attribute subType :>> subType : Profile::DataTypes::DataItemSubTypeEnum :> subType default "OVERRIDE";
            }
            part def Strain :> Sample {
                doc /* {{def(SampleEnum::STRAIN)}}*/
                constant attribute units :>> Acceleration::units : Profile::DataTypes::UnitEnum :> Acceleration::units default units::PERCENT;
                constant attribute type :>> type : Profile::DataTypes::SampleEnum :> Acceleration::type default type::STRAIN;
            }
            part def Temperature :> Sample {
                doc /* {{def(SampleEnum::TEMPERATURE)}}*/
                constant attribute units :>> Acceleration::units : Profile::DataTypes::UnitEnum :> Acceleration::units default units::CELSIUS;
                constant attribute type :>> type : Profile::DataTypes::SampleEnum :> Acceleration::type default type::TEMPERATURE;
            }
            part def Tension :> Sample {
                doc /* {{def(SampleEnum::TENSION)}}*/
                constant attribute units :>> Acceleration::units : Profile::DataTypes::UnitEnum :> Acceleration::units default units::NEWTON;
                constant attribute type :>> type : Profile::DataTypes::SampleEnum :> Acceleration::type default type::TENSION;
            }
            part def Tilt :> Sample {
                doc /* {{def(SampleEnum::TILT)}}*/
                constant attribute units :>> Acceleration::units : Profile::DataTypes::UnitEnum :> Acceleration::units default units::MICRO_RADIAN;
                constant attribute type :>> type : Profile::DataTypes::SampleEnum :> Acceleration::type default type::TILT;
            }
            part def Torque :> Sample {
                doc /* {{def(SampleEnum::TORQUE)}}*/
                constant attribute units :>> Acceleration::units : Profile::DataTypes::UnitEnum :> Acceleration::units default units::NEWTON_METER;
                constant attribute type :>> type : Profile::DataTypes::SampleEnum :> Acceleration::type default type::TORQUE;
            }
            part def Velocity :> Sample {
                doc /* {{def(SampleEnum::VELOCITY)}}*/
                constant attribute units :>> Acceleration::units : Profile::DataTypes::UnitEnum :> Acceleration::units default units::'MILLIMETER/SECOND';
                constant attribute type :>> type : Profile::DataTypes::SampleEnum :> Acceleration::type default type::VELOCITY;
            }
            part def Viscosity :> Sample {
                doc /* {{def(SampleEnum::VISCOSITY)}}*/
                constant attribute units :>> Acceleration::units : Profile::DataTypes::UnitEnum :> Acceleration::units default units::PASCAL_SECOND;
                constant attribute type :>> type : Profile::DataTypes::SampleEnum :> Acceleration::type default type::VISCOSITY;
            }
            part def Voltage :> Sample {
                doc /* {{def(SampleEnum::VOLTAGE)}}*/
                constant attribute units :>> Acceleration::units : Profile::DataTypes::UnitEnum :> Acceleration::units default units::VOLT;
                constant attribute type :>> type : Profile::DataTypes::SampleEnum :> Acceleration::type default type::VOLTAGE;
            }
            part def 'Voltage.Alternating' :> Voltage {
                doc 
                /* alternating voltage or current. 
                 *
                 * If not specified further in statistic, defaults to RMS voltage. 
                 *
                 * **DEPRECATED** in *Version 1.6*.*/
                constant attribute subType :>> subType : Profile::DataTypes::DataItemSubTypeEnum :> subType default "ALTERNATING";
            }
            part def 'Voltage.Direct' :> Voltage {
                doc 
                /* DC current or voltage.
                 *
                 * **DEPRECATED** in *Version 1.6*.*/
                constant attribute subType :>> subType : Profile::DataTypes::DataItemSubTypeEnum :> subType default "DIRECT";
            }
            part def 'Voltage.Actual' :> Voltage {
                doc 
                /* measured or reported value of an {{term(observation)}}.
                 *
                 * **DEPRECATED** in *Version 1.6*.*/
                constant attribute subType :>> subType : Profile::DataTypes::DataItemSubTypeEnum :> subType default "ACTUAL";
            }
            part def 'Voltage.Target' :> Voltage {
                doc 
                /* goal of the operation or process.
                 *
                 * **DEPRECATED** in *Version 1.6*.*/
                constant attribute subType :>> subType : Profile::DataTypes::DataItemSubTypeEnum :> subType default "TARGET";
            }
            part def VoltAmpere :> Sample {
                doc /* {{def(SampleEnum::VOLT_AMPERE)}}*/
                constant attribute units :>> Acceleration::units : Profile::DataTypes::UnitEnum :> Acceleration::units default units::VOLT_AMPERE;
                constant attribute type :>> type : Profile::DataTypes::SampleEnum default type::VOLT_AMPERE;
            }
            part def VoltAmpereReactive :> Sample {
                doc /* {{def(SampleEnum::VOLT_AMPERE_REACTIVE)}}*/
                constant attribute units :>> Acceleration::units : Profile::DataTypes::UnitEnum :> Acceleration::units default units::VOLT_AMPERE_REACTIVE;
                constant attribute type :>> type : Profile::DataTypes::SampleEnum default type::VOLT_AMPERE_REACTIVE;
            }
            part def VolumeFluid :> Sample {
                doc /* {{def(SampleEnum::VOLUME_FLUID)}}*/
                constant attribute units :>> Acceleration::units : Profile::DataTypes::UnitEnum :> Acceleration::units default units::MILLILITER;
                constant attribute type :>> type : Profile::DataTypes::SampleEnum default type::VOLUME_FLUID;
            }
            part def 'VolumeFluid.Actual' :> VolumeFluid {
                doc /* measured or reported value of an {{term(observation)}}.*/
                constant attribute subType :>> subType : Profile::DataTypes::DataItemSubTypeEnum :> subType default subType::ACTUAL;
            }
            part def 'VolumeFluid.Consumed' :> VolumeFluid {
                doc /* reported or measured value of the amount used in the manufacturing process.*/
                constant attribute subType :>> subType : Profile::DataTypes::DataItemSubTypeEnum :> subType default subType::CONSUMED;
            }
            part def VolumeSpatial :> Sample {
                doc /* {{def(SampleEnum::VOLUME_SPATIAL)}}*/
                constant attribute units :>> Acceleration::units : Profile::DataTypes::UnitEnum :> Acceleration::units default units::CUBIC_MILLIMETER;
                constant attribute type :>> type : Profile::DataTypes::SampleEnum default type::VOLUME_SPATIAL;
            }
            part def 'VolumeSpatial.Actual' :> VolumeSpatial {
                doc /* measured or reported value of an {{term(observation)}}.*/
                constant attribute subType :>> subType : Profile::DataTypes::DataItemSubTypeEnum :> subType default "ACTUAL";
            }
            part def 'VolumeSpatial.Consumed' :> VolumeSpatial {
                doc /* reported or measured value of the amount used in the manufacturing process.*/
                constant attribute subType :>> subType : Profile::DataTypes::DataItemSubTypeEnum :> subType default "CONSUMED";
            }
            part def Wattage :> Sample {
                doc /* {{def(SampleEnum::WATTAGE)}}*/
                constant attribute units :>> Acceleration::units : Profile::DataTypes::UnitEnum :> Acceleration::units default units::WATT;
                constant attribute type :>> type : Profile::DataTypes::SampleEnum default type::WATTAGE;
            }
            part def 'Wattage.Actual' :> Wattage {
                doc /* measured or reported value of an {{term(observation)}}.*/
                constant attribute subType :>> subType : Profile::DataTypes::DataItemSubTypeEnum :> subType default "ACTUAL";
            }
            part def 'Wattage.Target' :> Wattage {
                doc /* goal of the operation or process.*/
                constant attribute subType :>> subType : Profile::DataTypes::DataItemSubTypeEnum :> subType default "TARGET";
            }
            part def AmperageDC :> Sample {
                doc /* {{def(SampleEnum::AMPERAGE_DC)}}*/
                constant attribute units :>> Acceleration::type : Profile::DataTypes::UnitEnum :> Acceleration::type default units::AMPERE;
                constant attribute type :>> Acceleration::type : Profile::DataTypes::SampleEnum :> Acceleration::type default type::AMPERAGE_DC;
                constant attribute subType :>> subType : Profile::DataTypes::DataItemSubTypeEnum :> subType;
            }
            part def 'AmperageDC.Actual' :> AmperageDC {
                doc /* measured or reported value of an {{term(observation)}}.*/
                constant attribute subType :>> Acceleration::subType : Profile::DataTypes::DataItemSubTypeEnum :> Acceleration::subType default subType::ACTUAL;
            }
            part def 'AmperageDC.Commanded' :> AmperageDC {
                doc /* directive value including adjustments such as an offset or overrides.*/
                constant attribute subType :>> Acceleration::subType : Profile::DataTypes::DataItemSubTypeEnum :> Acceleration::subType default subType::COMMANDED;
            }
            part def 'AmperageDC.Programmed' :> AmperageDC {
                doc /* directive value without offsets and adjustments.*/
                constant attribute subType :>> Acceleration::subType : Profile::DataTypes::DataItemSubTypeEnum :> Acceleration::subType default subType::PROGRAMMED;
            }
            part def AmperageAC :> Sample {
                doc /* {{def(SampleEnum::AMPERAGE_AC)}}*/
                constant attribute units :>> Acceleration::type : Profile::DataTypes::UnitEnum :> Acceleration::type default units::AMPERE;
                constant attribute type :>> type : Profile::DataTypes::SampleEnum :> Acceleration::type default type::AMPERAGE_AC;
                constant attribute subType :>> subType : Profile::DataTypes::DataItemSubTypeEnum :> subType;
            }
            part def 'AmperageAC.Actual' :> AmperageAC {
                doc /* measured or reported value of an {{term(observation)}}.*/
                constant attribute subType :>> Acceleration::subType : Profile::DataTypes::DataItemSubTypeEnum :> Acceleration::subType default subType::ACTUAL;
            }
            part def 'AmperageAC.Commanded' :> AmperageAC {
                doc /* directive value including adjustments such as an offset or overrides.*/
                constant attribute subType :>> Acceleration::subType : Profile::DataTypes::DataItemSubTypeEnum :> Acceleration::subType default subType::COMMANDED;
            }
            part def 'AmperageAC.Programmed' :> AmperageAC {
                doc /* directive value without offsets and adjustments.*/
                constant attribute subType :>> Acceleration::subType : Profile::DataTypes::DataItemSubTypeEnum :> Acceleration::subType default subType::PROGRAMMED;
            }
            part def 'VoltageAC.Actual' :> VoltageAC {
                doc /* measured or reported value of an {{term(observation)}}.*/
                constant attribute subType :>> Acceleration::subType : Profile::DataTypes::DataItemSubTypeEnum :> Acceleration::subType default subType::ACTUAL;
            }
            part def VoltageAC :> Sample {
                doc /* {{def(SampleEnum::VOLTAGE_AC)}}*/
                constant attribute units :>> Acceleration::type : Profile::DataTypes::UnitEnum :> Acceleration::type default units::VOLT;
                constant attribute type :>> type : Profile::DataTypes::SampleEnum :> Acceleration::type default type::VOLTAGE_AC;
                constant attribute subType [1] :>> subType : Profile::DataTypes::DataItemSubTypeEnum :> subType;
            }
            part def 'VoltageAC.Commanded' :> VoltageAC {
                doc /* directive value including adjustments such as an offset or overrides.*/
                constant attribute subType :>> Acceleration::subType : Profile::DataTypes::DataItemSubTypeEnum :> Acceleration::subType default subType::COMMANDED;
            }
            part def 'VoltageAC.Programmed' :> VoltageAC {
                doc /* directive value without offsets and adjustments.*/
                constant attribute subType :>> Acceleration::subType : Profile::DataTypes::DataItemSubTypeEnum :> Acceleration::subType default subType::PROGRAMMED;
            }
            part def 'VoltageDC.Actual' :> VoltageDC {
                doc /* measured or reported value of an {{term(observation)}}.*/
                constant attribute subType :>> Acceleration::subType : Profile::DataTypes::DataItemSubTypeEnum :> Acceleration::subType default subType::ACTUAL;
            }
            part def 'VoltageDC.Commanded' :> VoltageDC {
                doc /* directive value including adjustments such as an offset or overrides.*/
                constant attribute subType :>> Acceleration::subType : Profile::DataTypes::DataItemSubTypeEnum :> Acceleration::subType default subType::COMMANDED;
            }
            part def 'VoltageDC.Programmed' :> VoltageDC {
                doc /* directive value without offsets and adjustments.*/
                constant attribute subType :>> Acceleration::subType : Profile::DataTypes::DataItemSubTypeEnum :> Acceleration::subType default subType::PROGRAMMED;
            }
            part def VoltageDC :> Sample {
                doc /* {{def(SampleEnum::VOLTAGE_DC)}}*/
                constant attribute units :>> Acceleration::type : Profile::DataTypes::UnitEnum :> Acceleration::type default units::VOLT;
                constant attribute type :>> type : Profile::DataTypes::SampleEnum default type::VOLTAGE_DC;
                constant attribute subType [1] :>> subType : Profile::DataTypes::DataItemSubTypeEnum :> subType;
            }
            part def XDimension :> Sample {
                doc /* {{def(SampleEnum::X_DIMENSION)}}*/
                constant attribute units :>> Acceleration::units : Profile::DataTypes::UnitEnum :> Acceleration::units default units::MILLIMETER;
                constant attribute type :>> type : Profile::DataTypes::SampleEnum default type::X_DIMENSION;
            }
            part def YDimension :> Sample {
                doc /* {{def(SampleEnum::Y_DIMENSION)}}*/
                constant attribute units :>> Acceleration::units : Profile::DataTypes::UnitEnum :> Acceleration::units default units::MILLIMETER;
                constant attribute type :>> type : Profile::DataTypes::SampleEnum default type::Y_DIMENSION;
            }
            part def ZDimension :> Sample {
                doc /* {{def(SampleEnum::Z_DIMENSION)}}*/
                constant attribute units :>> Acceleration::units : Profile::DataTypes::UnitEnum :> Acceleration::units default units::MILLIMETER;
                constant attribute type :>> type : Profile::DataTypes::SampleEnum default type::Z_DIMENSION;
            }
            part def Diameter :> Sample {
                doc /* {{def(SampleEnum::DIAMETER)}}*/
                constant attribute units :>> Acceleration::units : Profile::DataTypes::UnitEnum :> Acceleration::units default units::MILLIMETER;
                constant attribute type :>> type : Profile::DataTypes::SampleEnum :> Acceleration::type default type::DIAMETER;
            }
            part def 'Orientation.Actual' :> Orientation {
                doc /* measured or reported value of an {{term(observation)}}.*/
                constant attribute subType :>> subType : Profile::DataTypes::DataItemSubTypeEnum :> subType default subType::ACTUAL;
            }
            part def Orientation :> Sample {
                doc /* {{def(SampleEnum::ORIENTATION)}}*/
                constant attribute units :>> Acceleration::type : Profile::DataTypes::UnitEnum :> Acceleration::type default units::DEGREE_3D;
                constant attribute type :>> type : Profile::DataTypes::SampleEnum :> Acceleration::type default type::ORIENTATION;
                attribute result [0..1] :>> Acceleration::result : Profile::DataTypes::float3d;
            }
            part def 'Orientation.Commanded' :> Orientation {
                doc /* directive value including adjustments such as an offset or overrides.*/
                constant attribute subType :>> subType : Profile::DataTypes::DataItemSubTypeEnum :> subType default subType::COMMANDED;
            }
            part def HumidityRelative :> Sample {
                doc /* {{def(SampleEnum::HUMIDITY_RELATIVE)}}*/
                constant attribute units :>> Acceleration::type : Profile::DataTypes::UnitEnum :> Acceleration::type default units::PERCENT;
                constant attribute type :>> type : Profile::DataTypes::SampleEnum :> Acceleration::type default type::HUMIDITY_RELATIVE;
            }
            part def 'HumidityRelative.Commanded' :> HumidityRelative {
                doc /* directive value including adjustments such as an offset or overrides.*/
                constant attribute subType :>> subType : Profile::DataTypes::DataItemSubTypeEnum :> subType default subType::COMMANDED;
            }
            part def 'HumidityRelative.Actual' :> HumidityRelative {
                doc /* measured or reported value of an {{term(observation)}}.*/
                constant attribute subType :>> subType : Profile::DataTypes::DataItemSubTypeEnum :> subType default subType::ACTUAL;
            }
            part def HumidityAbsolute :> Sample {
                doc /* {{def(SampleEnum::HUMIDITY_ABSOLUTE)}}*/
                constant attribute units :>> Acceleration::type : Profile::DataTypes::UnitEnum :> Acceleration::type default units::'GRAM/CUBIC_METER';
                constant attribute type :>> type : Profile::DataTypes::SampleEnum :> Acceleration::type default type::HUMIDITY_ABSOLUTE;
            }
            part def 'HumidityAbsolute.Actual' :> HumidityAbsolute {
                doc /* measured or reported value of an {{term(observation)}}.*/
                constant attribute subType :>> subType : Profile::DataTypes::DataItemSubTypeEnum :> subType default subType::ACTUAL;
            }
            part def 'HumidityAbsolute.Commanded' :> HumidityAbsolute {
                doc /* directive value including adjustments such as an offset or overrides.*/
                constant attribute subType :>> subType : Profile::DataTypes::DataItemSubTypeEnum :> subType default subType::COMMANDED;
            }
            part def HumiditySpecific :> Sample {
                doc /* {{def(SampleEnum::HUMIDITY_SPECIFIC)}}*/
                constant attribute units :>> Acceleration::type : Profile::DataTypes::UnitEnum :> Acceleration::type default units::PERCENT;
                constant attribute type :>> type : Profile::DataTypes::SampleEnum :> Acceleration::type default type::HUMIDITY_SPECIFIC;
            }
            part def 'HumiditySpecific.Actual' :> HumiditySpecific {
                doc /* measured or reported value of an {{term(observation)}}.*/
                constant attribute subType :>> subType : Profile::DataTypes::DataItemSubTypeEnum :> subType default subType::ACTUAL;
            }
            part def 'HumiditySpecific.Commanded' :> HumiditySpecific {
                doc /* directive value including adjustments such as an offset or overrides.*/
                constant attribute subType :>> subType : Profile::DataTypes::DataItemSubTypeEnum :> subType default subType::COMMANDED;
            }
            part def 'AngularDeceleration.Actual' :> AngularDeceleration {
                doc /* measured or reported value of an {{term(observation)}}.*/
                constant attribute subType :>> Acceleration::subType : Profile::DataTypes::DataItemSubTypeEnum :> Acceleration::subType default subType::ACTUAL;
            }
            part def 'Deceleration.Programmed' :> Deceleration {
                doc /* directive value without offsets and adjustments.*/
                constant attribute subType :>> Acceleration::subType : Profile::DataTypes::DataItemSubTypeEnum :> Acceleration::subType default subType::PROGRAMMED;
            }
            part def 'AngularDeceleration.Programmed' :> AngularDeceleration {
                doc /* directive value without offsets and adjustments.*/
                constant attribute subType :>> Acceleration::subType : Profile::DataTypes::DataItemSubTypeEnum :> Acceleration::subType default subType::PROGRAMMED;
            }
            part def PressurizationRate :> Sample {
                doc /* {{def(SampleEnum::PRESSURIZATION_RATE)}}*/
                constant attribute units :>> Acceleration::units : Profile::DataTypes::UnitEnum :> Acceleration::units default units::'PASCAL/SECOND';
                constant attribute type :>> type : Profile::DataTypes::SampleEnum :> Acceleration::type default type::PRESSURIZATION_RATE;
            }
            part def 'AngularDeceleration.Commanded' :> AngularDeceleration {
                doc /* directive value including adjustments such as an offset or overrides.*/
                constant attribute subType :>> Acceleration::subType : Profile::DataTypes::DataItemSubTypeEnum :> Acceleration::subType default subType::COMMANDED;
            }
            part def Deceleration :> Sample {
                doc /* {{def(SampleEnum::DECELERATION)}}*/
                constant attribute units :>> Acceleration::units : Profile::DataTypes::UnitEnum :> Acceleration::units default units::'MILLIMETER/SECOND^2';
                constant attribute type :>> type : Profile::DataTypes::SampleEnum :> Acceleration::type default type::DECELERATION;
                constant attribute subType :>> subType : Profile::DataTypes::DataItemSubTypeEnum :> subType default subType::ACTUAL;
            }
            part def AssetUpdateRate :> Sample {
                doc /* {{def(SampleEnum::ASSET_UPDATE_RATE)}}*/
                constant attribute units :>> Acceleration::units : Profile::DataTypes::UnitEnum :> Acceleration::units default units::'COUNT/SECOND';
                constant attribute type :>> type : Profile::DataTypes::SampleEnum :> Acceleration::type default type::ASSET_UPDATE_RATE;
            }
            part def AngularDeceleration :> Sample {
                doc /* {{def(SampleEnum::ANGULAR_DECELERATION)}}*/
                constant attribute units :>> Acceleration::units : Profile::DataTypes::UnitEnum :> Acceleration::units default units::'DEGREE/SECOND^2';
                constant attribute type :>> type : Profile::DataTypes::SampleEnum :> Acceleration::type default type::ANGULAR_DECELERATION;
                constant attribute subType :>> subType : Profile::DataTypes::DataItemSubTypeEnum :> subType default subType::ACTUAL;
            }
            part def ObservationUpdateRate :> Sample {
                doc /* {{def(SampleEnum::OBSERVATION_UPDATE_RATE)}}*/
                constant attribute units :>> Acceleration::units : Profile::DataTypes::UnitEnum :> Acceleration::units default units::'COUNT/SECOND';
                constant attribute type :>> type : Profile::DataTypes::SampleEnum :> Acceleration::type default type::OBSERVATION_UPDATE_RATE;
            }
            part def 'Deceleration.Commanded' :> Deceleration {
                doc /* directive value including adjustments such as an offset or overrides.*/
                constant attribute subType :>> Acceleration::subType : Profile::DataTypes::DataItemSubTypeEnum :> Acceleration::subType default subType::COMMANDED;
            }
            part def 'Deceleration.Actual' :> Deceleration {
                doc /* measured or reported value of an {{term(observation)}}.*/
                constant attribute subType :>> Acceleration::subType : Profile::DataTypes::DataItemSubTypeEnum :> Acceleration::subType default subType::ACTUAL;
            }
            part def PressureAbsolute :> Sample {
                doc /* The force per unit area measured relative to a vacuum.*/
                constant attribute units :>> Acceleration::units : Profile::DataTypes::UnitEnum :> Acceleration::units default units::PASCAL;
                constant attribute type :>> Acceleration::type : Profile::DataTypes::SampleEnum :> Acceleration::type default type::PRESSURE_ABSOLUTE;
            }
            part def 'Acceleration.Actual' :> Acceleration {
                doc /* measured or reported value of an {{term(observation)}}.*/
                constant attribute subType :>> subType : Profile::DataTypes::DataItemSubTypeEnum :> subType default subType::ACTUAL;
            }
            part def 'VolumeFluid.Part' :> VolumeFluid {
                doc /* reported or measured value of amount included in the {{term(part)}}.*/
                constant attribute subType :>> subType : Profile::DataTypes::DataItemSubTypeEnum :> subType default subType::PART;
            }
            part def 'AngularAcceleration.Programmed' :> AngularAcceleration {
                doc /* directive value without offsets and adjustments.*/
                constant attribute subType :>> 'AngularDeceleration.Actual'::subType : Profile::DataTypes::DataItemSubTypeEnum :> 'AngularDeceleration.Actual'::subType default subType::PROGRAMMED;
            }
            part def 'PressurizationRate.Commanded' :> PressurizationRate {
                doc /* directive value including adjustments such as an offset or overrides.*/
                constant attribute subType :>> subType : Profile::DataTypes::DataItemSubTypeEnum :> subType default subType::COMMANDED;
            }
            part def 'Acceleration.Programmed' :> Acceleration {
                doc /* directive value without offsets and adjustments.*/
                constant attribute subType :>> subType : Profile::DataTypes::DataItemSubTypeEnum :> subType default subType::PROGRAMMED;
            }
            part def 'Acceleration.Commanded' :> Acceleration {
                doc /* directive value including adjustments such as an offset or overrides.*/
                constant attribute subType :>> subType : Profile::DataTypes::DataItemSubTypeEnum :> subType default subType::COMMANDED;
            }
            part def 'VolumeFluid.Waste' :> VolumeFluid {
                doc /* reported or measured value of the amount discarded.*/
                constant attribute subType :>> subType : Profile::DataTypes::DataItemSubTypeEnum :> subType default subType::WASTE;
            }
            part def 'VolumeSpatial.Part' :> VolumeSpatial {
                doc /* reported or measured value of amount included in the {{term(part)}}.*/
                constant attribute subType :>> subType : Profile::DataTypes::DataItemSubTypeEnum :> subType default subType::PART;
            }
            part def 'VolumeFluid.Start' :> VolumeFluid {
                doc /* boundary when an activity or an event commences.*/
                constant attribute subType :>> subType : Profile::DataTypes::DataItemSubTypeEnum :> subType default subType::START;
            }
            part def 'AngularAcceleration.Actual' :> AngularAcceleration {
                doc /* measured or reported value of an {{term(observation)}}.*/
                constant attribute subType :>> 'AngularDeceleration.Actual'::subType : Profile::DataTypes::DataItemSubTypeEnum :> 'AngularDeceleration.Actual'::subType default subType::ACTUAL;
            }
            part def 'VolumeSpatial.Waste' :> VolumeSpatial {
                doc /* reported or measured value of the amount discarded*/
                constant attribute subType :>> subType : Profile::DataTypes::DataItemSubTypeEnum :> subType default subType::WASTE;
            }
            part def 'PressurizationRate.Actual' :> PressurizationRate {
                doc /* measured or reported value of an {{term(observation)}}.*/
                constant attribute subType :>> subType : Profile::DataTypes::DataItemSubTypeEnum :> subType default subType::ACTUAL;
            }
            part def 'VolumeSpatial.Ended' :> VolumeSpatial {
                doc /* boundary when an activity or an event terminates.*/
                constant attribute subType :>> subType : Profile::DataTypes::DataItemSubTypeEnum :> subType default subType::ENDED;
            }
            part def 'AngularAcceleration.Commanded' :> AngularAcceleration {
                doc /* directive value including adjustments such as an offset or overrides.*/
                constant attribute subType :>> 'AngularDeceleration.Actual'::subType : Profile::DataTypes::DataItemSubTypeEnum :> 'AngularDeceleration.Actual'::subType default subType::COMMANDED;
            }
            part def 'PressurizationRate.Programmed' :> PressurizationRate {
                doc /* directive value without offsets and adjustments.*/
                constant attribute subType :>> subType : Profile::DataTypes::DataItemSubTypeEnum :> subType default subType::PROGRAMMED;
            }
            part def 'VolumeSpatial.Start' :> VolumeSpatial {
                doc /* boundary when an activity or an event commences.*/
                constant attribute subType :>> subType : Profile::DataTypes::DataItemSubTypeEnum :> subType default subType::START;
            }
            part def 'VolumeFluid.Ended' :> VolumeFluid {
                doc /* boundary when an activity or an event terminates.*/
                constant attribute subType :>> subType : Profile::DataTypes::DataItemSubTypeEnum :> subType default subType::ENDED;
            }
            part def Openness :> Sample {
                doc /* {{def(SampleEnum::OPENNESS)}}*/
                constant attribute units :>> units : Profile::DataTypes::UnitEnum :> units default units::PERCENT;
                constant attribute type :>> type : Profile::DataTypes::SampleEnum :> type default type::OPENNESS;
            }
            part def 'GlobalPosition.Actual' :> GlobalPosition {
                doc /* measured or reported value of an {{term(observation)}}.*/
                constant attribute subType :>> subType : Profile::DataTypes::DataItemSubTypeEnum :> subType default subType::ACTUAL;
            }
            part def 'GlobalPosition.Commanded' :> GlobalPosition {
                doc /* directive value including adjustments such as an offset or overrides.*/
                constant attribute subType :>> subType : Profile::DataTypes::DataItemSubTypeEnum :> subType default subType::COMMANDED;
            }
            part def DewPoint :> Sample {
                doc /* {{def(SampleEnum::DEW_POINT)}}*/
                constant attribute units :>> Acceleration::units : Profile::DataTypes::UnitEnum :> Acceleration::units default units::CELSIUS;
                constant attribute type :>> type : Profile::DataTypes::SampleEnum :> Acceleration::type default type::DEW_POINT;
            }
            part def GravitationalForce :> Sample {
                doc 
                /* {{def(SampleEnum::GRAVITATIONAL_FORCE)}}
                 *
                 * > Note: $$Mass\times GravitationalAcceleration$$*/
                constant attribute units :>> Acceleration::units : Profile::DataTypes::NativeUnitEnum :> Acceleration::units default units::GRAVITATIONAL_FORCE;
                constant attribute type :>> type : Profile::DataTypes::SampleEnum :> Acceleration::type default type::GRAVITATIONAL_FORCE;
            }
            part def GravitationalAcceleration :> Sample {
                doc 
                /* {{def(SampleEnum::GRAVITATIONAL_ACCELERATION)}}
                 *
                 */
                constant attribute units :>> Acceleration::units : Profile::DataTypes::NativeUnitEnum :> Acceleration::units default units::GRAVITATIONAL_ACCELERATION;
                constant attribute type :>> type : Profile::DataTypes::SampleEnum :> Acceleration::type default type::GRAVITATIONAL_ACCELERATION;
            }
            part def BatteryCapacity :> Sample {
                doc /* {{def(SampleEnum::BATTERY_CAPACITY)}}*/
                constant attribute units :>> Acceleration::units : Profile::DataTypes::UnitEnum :> Acceleration::units default units::COULOMB;
                constant attribute type :>> type : Profile::DataTypes::SampleEnum :> type default type::BATTERY_CAPACITY;
                constant attribute subType :>> subType : Profile::DataTypes::DataItemSubTypeEnum :> subType default subType::ACTUAL;
            }
            part def 'BatteryCapacity.Actual' :> BatteryCapacity {
                doc /* measured or reported value of an {{term(observation)}}.*/
                constant attribute subType :>> subType : Profile::DataTypes::DataItemSubTypeEnum :> subType default subType::ACTUAL;
            }
            part def 'BatteryCapacity.Target' :> BatteryCapacity {
                doc /* goal of the operation or process.*/
                constant attribute subType :>> subType : Profile::DataTypes::DataItemSubTypeEnum :> subType default subType::TARGET;
            }
            part def DischargeRate :> Sample {
                doc /* {{def(SampleEnum::DISCHARGE_RATE)}}*/
                constant attribute units :>> Acceleration::units : Profile::DataTypes::UnitEnum :> Acceleration::units default units::AMPERE;
                constant attribute type :>> type : Profile::DataTypes::SampleEnum :> type default type::DISCHARGE_RATE;
                constant attribute subType :>> subType : Profile::DataTypes::DataItemSubTypeEnum :> subType default subType::ACTUAL;
            }
            part def 'DischargeRate.Actual' :> DischargeRate {
                doc /* measured or reported value of an {{term(observation)}}.*/
                constant attribute subType :>> subType : Profile::DataTypes::DataItemSubTypeEnum :> subType default subType::ACTUAL;
            }
            part def 'DischargeRate.Target' :> DischargeRate {
                doc /* goal of the operation or process.*/
                constant attribute subType :>> subType : Profile::DataTypes::DataItemSubTypeEnum :> subType default subType::TARGET;
            }
            part def ChargeRate :> Sample {
                doc /* {{def(SampleEnum::CHARGE_RATE)}}*/
                constant attribute units :>> Acceleration::units : Profile::DataTypes::UnitEnum :> Acceleration::units default units::AMPERE;
                constant attribute type :>> type : Profile::DataTypes::SampleEnum :> type default type::CHARGE_RATE;
                constant attribute subType :>> subType : Profile::DataTypes::DataItemSubTypeEnum :> subType default subType::ACTUAL;
            }
            part def 'ChargeRate.Actual' :> ChargeRate {
                doc /* measured or reported value of an {{term(observation)}}.*/
                constant attribute subType :>> subType : Profile::DataTypes::DataItemSubTypeEnum :> subType default subType::ACTUAL;
            }
            part def 'ChargeRate.Target' :> ChargeRate {
                doc /* goal of the operation or process.*/
                constant attribute subType :>> subType : Profile::DataTypes::DataItemSubTypeEnum :> subType default subType::TARGET;
            }
            part def BatteryCharge :> Sample {
                doc /* {{def(SampleEnum::BATTERY_CHARGE)}}*/
                constant attribute units :>> Acceleration::units : Profile::DataTypes::UnitEnum :> Acceleration::units default units::PERCENT;
                constant attribute type :>> type : Profile::DataTypes::SampleEnum :> type default type::BATTERY_CHARGE;
                constant attribute subType :>> subType : Profile::DataTypes::DataItemSubTypeEnum :> subType default subType::ACTUAL;
            }
            part def 'BatteryCharge.Actual' :> BatteryCharge {
                doc /* measured or reported value of an {{term(observation)}}.*/
                constant attribute subType :>> subType : Profile::DataTypes::DataItemSubTypeEnum :> subType default subType::ACTUAL;
            }
            part def 'BatteryCharge.Target' :> BatteryCharge {
                doc /* goal of the operation or process.*/
                constant attribute subType :>> subType : Profile::DataTypes::DataItemSubTypeEnum :> subType default subType::TARGET;
            }
            part def SettlingError :> Sample {
                doc /* {{def(SampleEnum::SETTLING_ERROR)}}*/
                constant attribute units :>> Acceleration::units : Profile::DataTypes::UnitEnum :> Acceleration::units default units::COUNT;
                constant attribute type :>> type : Profile::DataTypes::SampleEnum :> type default type::SETTLING_ERROR;
            }
            part def 'SettlingError.Actual' :> SettlingError {
                doc /* measured or reported value of an {{term(observation)}}.*/
                constant attribute subType : Profile::DataTypes::DataItemSubTypeEnum default subType::ACTUAL;
            }
            part def SettlingErrorLinear :> Sample {
                doc /* {{def(SampleEnum::SETTLING_ERROR_LINEAR)}}*/
                constant attribute units :>> Acceleration::units : Profile::DataTypes::UnitEnum :> Acceleration::units default units::MILLIMETER;
                constant attribute type :>> type : Profile::DataTypes::SampleEnum :> type default type::SETTLING_ERROR_LINEAR;
            }
            part def 'SettlingErrorLinear.Actual' :> SettlingErrorLinear {
                doc /* measured or reported value of an {{term(observation)}}.*/
                constant attribute subType : Profile::DataTypes::DataItemSubTypeEnum default subType::ACTUAL;
            }
            part def SettlingErrorAngular :> Sample {
                doc /* {{def(SampleEnum::SETTLING_ERROR_ANGULAR)}}*/
                constant attribute units :>> Acceleration::units : Profile::DataTypes::UnitEnum :> Acceleration::units default units::DEGREE;
                constant attribute type :>> type : Profile::DataTypes::SampleEnum :> type default type::SETTLING_ERROR_ANGULAR;
            }
            part def 'SettlingErrorAngular.Actual' :> SettlingErrorAngular {
                doc /* measured or reported value of an {{term(observation)}}.*/
                constant attribute subType : Profile::DataTypes::DataItemSubTypeEnum default subType::ACTUAL;
            }
            part def FollowingError :> Sample {
                doc /* {{def(SampleEnum::FOLLOWING_ERROR)}}*/
                constant attribute units :>> Acceleration::units : Profile::DataTypes::UnitEnum :> Acceleration::units default units::COUNT;
                constant attribute type :>> type : Profile::DataTypes::SampleEnum :> type default type::FOLLOWING_ERROR;
            }
            part def 'FollowingError.Actual' :> FollowingError {
                doc /* measured or reported value of an {{term(observation)}}.*/
                constant attribute subType : Profile::DataTypes::DataItemSubTypeEnum default subType::ACTUAL;
            }
            part def FollowingErrorAngular :> Sample {
                doc /* {{def(SampleEnum::FOLLOWING_ERROR_ANGULAR)}}*/
                constant attribute units :>> Acceleration::units : Profile::DataTypes::UnitEnum :> Acceleration::units default units::DEGREE;
                constant attribute type :>> type : Profile::DataTypes::SampleEnum :> type default type::FOLLOWING_ERROR_ANGULAR;
            }
            part def FollowingErrorLinear :> Sample {
                doc /* {{def(SampleEnum::FOLLOWING_ERROR_LINEAR)}}*/
                constant attribute units :>> Acceleration::units : Profile::DataTypes::UnitEnum :> Acceleration::units default units::MILLIMETER;
                constant attribute type :>> type : Profile::DataTypes::SampleEnum :> type default type::FOLLOWING_ERROR_LINEAR;
            }
            part def 'FollowingErrorAngular.Actual' :> FollowingErrorAngular {
                doc /* measured or reported value of an {{term(observation)}}.*/
                constant attribute subType : Profile::DataTypes::DataItemSubTypeEnum default subType::ACTUAL;
            }
            part def 'FollowingErrorLinear.Actual' :> FollowingErrorLinear {
                doc /* measured or reported value of an {{term(observation)}}.*/
                constant attribute subType : Profile::DataTypes::DataItemSubTypeEnum default subType::ACTUAL;
            }
            part def DisplacementLinear :> Sample {
                doc 
                /* {{def(SampleEnum::DISPLACEMENT_LINEAR)}}
                 *
                 * > Note: The displacement vector **MAY** be defined by the motion of the owning {{block(Component)}}.*/
                constant attribute units :>> Acceleration::units : Profile::DataTypes::UnitEnum :> Acceleration::units default units::MILLIMETER;
                constant attribute type :>> type : Profile::DataTypes::SampleEnum :> Acceleration::type default type::DISPLACEMENT_LINEAR;
            }
            part def DisplacementAngular :> Sample {
                doc 
                /* {{def(SampleEnum::DISPLACEMENT_ANGULAR)}}
                 *
                 * > Note: The displacement vector **MAY** be defined by the motion of the owning {{block(Component)}}.*/
                constant attribute units :>> Acceleration::units : Profile::DataTypes::UnitEnum :> Acceleration::units default units::DEGREE;
                constant attribute type :>> type : Profile::DataTypes::SampleEnum :> Acceleration::type default type::DISPLACEMENT_ANGULAR;
            }
            part def PositionCartesian :> Sample {
                doc /* {{def(SampleEnum::POSITION_CARTESIAN)}}*/
                constant attribute units :>> Acceleration::units : Profile::DataTypes::UnitEnum :> Acceleration::units default units::MILLIMETER_3D;
                constant attribute type :>> type : Profile::DataTypes::SampleEnum :> Acceleration::type default type::POSITION_CARTESIAN;
                attribute result [0..1] :>> Acceleration::result : Profile::DataTypes::float3d;
            }
            part def Resistivity :> Sample {
                doc /* {{def(SampleEnum::RESISTIVITY)}}*/
                constant attribute units :>> Acceleration::units : Profile::DataTypes::UnitEnum :> Acceleration::units default units::OHM_METER;
                constant attribute type :>> type : Profile::DataTypes::SampleEnum :> type default type::RESISTIVITY;
            }
            part def FillHeight :> Sample {
                doc /* {{def(SampleEnum::FILL_HEIGHT)}}*/
                constant attribute units :>> Acceleration::units : Profile::DataTypes::UnitEnum :> Acceleration::units default units::MILLIMETER;
                constant attribute type :>> type : Profile::DataTypes::SampleEnum :> type default type::FILL_HEIGHT;
            }
            part def 'FillHeight.Actual' :> FillHeight {
                doc /* {{def(SampleEnum::FILL_HEIGHT)}} that is {{def(DataItemSubTypeEnum::ACTUAL)}}*/
                constant attribute subType : Profile::DataTypes::DataItemSubTypeEnum default subType::ACTUAL;
            }
            part def 'FillHeight.Target' :> FillHeight {
                doc /* {{def(SampleEnum::FILL_HEIGHT)}} that is {{def(DataItemSubTypeEnum::TARGET)}}*/
                constant attribute subType : Profile::DataTypes::DataItemSubTypeEnum default subType::TARGET;
            }
            part def ParticleCount :> Sample {
                doc /* {{def(SampleEnum::PARTICLE_COUNT)}}*/
                constant attribute units :>> Acceleration::units : Profile::DataTypes::UnitEnum :> Acceleration::units default units::COUNT;
                constant attribute type :>> type : Profile::DataTypes::SampleEnum :> type default type::PARTICLE_COUNT;
            }
            part def 'ParticleCount.Gas' :> ParticleCount {
                doc /* {{def(SampleEnum::PARTICLE_COUNT)}} for a {{def(DataItemSubType::GAS)}}*/
                constant attribute subType : Profile::DataTypes::DataItemSubTypeEnum default subType::GAS;
            }
            part def 'ParticleCount.Liquid' :> ParticleCount {
                doc /* {{def(SampleEnum::PARTICLE_COUNT)}} for a {{def(DataItemSubType::LIQUID)}}*/
                constant attribute subType : Profile::DataTypes::DataItemSubTypeEnum default subType::LIQUID;
            }
            part def 'ParticleCount.Solid' :> ParticleCount {
                doc /* {{def(SampleEnum::PARTICLE_COUNT)}} for a {{def(DataItemSubType::SOLID)}}*/
                constant attribute subType : Profile::DataTypes::DataItemSubTypeEnum default subType::SOLID;
            }
            part def ParticleSize :> Sample {
                doc /* {{def(SampleEnum::PARTICLE_SIZE)}}*/
                constant attribute units :>> Acceleration::units : Profile::DataTypes::UnitEnum :> Acceleration::units default units::MILLIMETER;
                constant attribute type :>> type : Profile::DataTypes::SampleEnum :> type default type::PARTICLE_SIZE;
            }
            part def WaterHardness :> Sample {
                doc /* {{def(SampleEnum::WATER_HARDNESS)}}*/
                constant attribute units :>> Acceleration::units : Profile::DataTypes::UnitEnum :> Acceleration::units default units::'MILLIGRAM/LITER';
                constant attribute type :>> type : Profile::DataTypes::SampleEnum :> type default type::WATER_HARDNESS;
            }
            doc /* This section provides semantic information for {{block(Sample)}} types.*/
        }
        package 'Event Types' {
            part def ActiveAxes :> Event {
                doc /* {{def(EventEnum::ACTIVE_AXES)}}*/
                attribute result [0..*] :>> result : Profile::DataTypes::string;
                constant attribute type :>> type : Profile::DataTypes::EventEnum :> type default type::ACTIVE_AXES;
            }
            part def ActuatorState :> Event {
                doc /* {{def(EventEnum::ACTUATOR_STATE)}}*/
                attribute result [0..1] :>> result : Profile::DataTypes::ActuatorStateEnum :> result;
                constant attribute type :>> type : Profile::DataTypes::EventEnum :> type default type::ACTUATOR_STATE;
            }
            part def Alarm :> Event {
                doc /* {{def(EventEnum::ALARM)}}*/
                constant attribute type :>> type : Profile::DataTypes::EventEnum :> type default type::ALARM;
                attribute code [1] : Profile::DataTypes::AlarmCodeEnum {
                    doc /* type of alarm.*/
                }
                attribute severity [1] : Profile::DataTypes::AlarmSeverityEnum {
                    doc /* severity of the alarm.*/
                }
                attribute nativeCode [1] : Profile::DataTypes::string {
                    doc /* native code for the piece of equipment.*/
                }
                attribute 'state' [1] : Profile::DataTypes::AlarmStateEnum {
                    doc /* state of the alarm.*/
                }
                attribute lang [0..1] : Profile::DataTypes::xslang {
                    doc 
                    /* specifies the language of the alarm text.
                     *
                     * See {{cite(IETF RFC 4646)}} (http://www.ietf.org/rfc/rfc4646.txt).*/
                }
            }
            part def AssetChanged :> Event {
                doc /* {{def(EventEnum::ASSET_CHANGED)}}*/
                attribute assetType [0..1] : Profile::DataTypes::string {
                    doc /* type of {{block(Asset)}} changed. See {{package(Asset Information Model)}} for details on the {{block(Asset)}} model.*/
                }
                constant attribute type :>> type : Profile::DataTypes::EventEnum :> type default type::ASSET_CHANGED;
                attribute hash [0..1] : Profile::DataTypes::string {
                    doc /* condensed message digest from a secure one-way hash function. {{cite(FIPS PUB 180-4)}}*/
                }
            }
            part def AssetRemoved :> Event {
                doc /* {{def(EventEnum::ASSET_REMOVED)}}*/
                attribute assetType [0..1] : Profile::DataTypes::string {
                    doc /* type of {{block(Asset)}} removed. See {{package(Asset Information Model)}} for details on the {{block(Asset)}} model.*/
                }
                constant attribute type :>> type : Profile::DataTypes::EventEnum :> type default type::ASSET_REMOVED;
                attribute hash [0..1] : Profile::DataTypes::string {
                    doc /* condensed message digest from a secure one-way hash function. {{cite(FIPS PUB 180-4)}}*/
                }
            }
            part def Availability :> Event {
                doc /* {{def(EventEnum::AVAILABILITY)}}*/
                attribute result [0..1] :>> result : Profile::DataTypes::AvailabilityEnum :> result;
                constant attribute type :>> type : Profile::DataTypes::EventEnum :> type default type::AVAILABILITY;
            }
            part def AxisCoupling :> Event {
                doc /* {{def(EventEnum::AXIS_COUPLING)}}*/
                attribute result [0..1] :>> result : Profile::DataTypes::AxisCouplingEnum :> result;
                constant attribute type :>> type : Profile::DataTypes::EventEnum :> type default type::AXIS_COUPLING;
            }
            part def AxisFeedrateOverride :> Event {
                doc /* {{def(EventEnum::AXIS_FEEDRATE_OVERRIDE)}}*/
                attribute result [0..1] :>> result : Profile::DataTypes::float;
                constant attribute type :>> type : Profile::DataTypes::EventEnum :> type default type::AXIS_FEEDRATE_OVERRIDE;
            }
            part def 'AxisFeedrateOverride.Jog' :> AxisFeedrateOverride {
                doc 
                /* relating to momentary activation of a function or a movement.
                 *
                 * **DEPRECATION WARNING**: May be deprecated in the future.*/
                comment /* Description*/
                constant attribute subType :>> subType : Profile::DataTypes::DataItemSubTypeEnum :> subType default "JOG";
                doc 
                /* When the `JOG` subtype of `AxisFeedrateOverride` is applied, the resulting commanded feedrate for the axis is limited to the value of the original `JOG` subtype of the `AxisFeedrate` multiplied by the value of the `JOG` subtype of
                 * `AxisFeedrateOverride`.*/
            }
            part def 'AxisFeedrateOverride.Programmed' :> AxisFeedrateOverride {
                doc /* directive value without offsets and adjustments.*/
                constant attribute subType :>> subType : Profile::DataTypes::DataItemSubTypeEnum :> subType default "PROGRAMMED";
            }
            part def 'AxisFeedrateOverride.Rapid' :> AxisFeedrateOverride {
                doc /* performing an operation faster or in less time than nominal rate.*/
                constant attribute subType :>> subType : Profile::DataTypes::DataItemSubTypeEnum :> subType default "RAPID";
            }
            part def AxisInterlock :> Event {
                doc /* {{def(EventEnum::AXIS_INTERLOCK)}}*/
                attribute result [0..1] :>> result : Profile::DataTypes::AxisInterlockEnum :> result;
                constant attribute type :>> type : Profile::DataTypes::EventEnum :> type default type::AXIS_INTERLOCK;
            }
            part def AxisState :> Event {
                doc /* {{def(EventEnum::AXIS_STATE)}}*/
                attribute result [0..1] :>> result : Profile::DataTypes::AxisStateEnum :> result;
                constant attribute type :>> type : Profile::DataTypes::EventEnum :> type default type::AXIS_STATE;
            }
            part def Block :> Event {
                doc /* {{def(EventEnum::BLOCK)}}*/
                constant attribute type :>> type : Profile::DataTypes::EventEnum :> type default type::BLOCK;
            }
            part def BlockCount :> Event {
                doc /* {{def(EventEnum::BLOCK_COUNT)}}*/
                attribute result [0..1] :>> result : Profile::DataTypes::integer;
                constant attribute type :>> type : Profile::DataTypes::EventEnum :> type default type::BLOCK_COUNT;
            }
            part def ChuckInterlock :> Event {
                doc /* {{def(EventEnum::CHUCK_INTERLOCK)}}*/
                attribute result [0..1] :>> result : Profile::DataTypes::ChuckInterlockEnum :> result;
                constant attribute type :>> type : Profile::DataTypes::EventEnum :> type default type::CHUCK_INTERLOCK;
            }
            part def 'ChuckInterlock.ManualUnclamp' :> ChuckInterlock {
                doc 
                /* indication of the state of an operator controlled interlock that can inhibit the ability to initiate an unclamp action of an electronically controlled chuck.
                 *
                 * When {{block(ChuckInterlockManualUnclamp)}} is `ACTIVE`, it is expected that a chuck cannot be unclamped until {{block(ChuckInterlockManualUnclamp)}} is set to `INACTIVE`. */
                constant attribute subType :>> subType : Profile::DataTypes::DataItemSubTypeEnum :> subType default "MANUAL_UNCLAMP";
            }
            part def ChuckState :> Event {
                doc /* {{def(EventEnum::CHUCK_STATE)}}*/
                attribute result [0..1] :>> result : Profile::DataTypes::ChuckStateEnum :> result;
                constant attribute type :>> type : Profile::DataTypes::EventEnum :> type default type::CHUCK_STATE;
            }
            part def Code :> Event {
                doc /* {{def(EventEnum::CODE)}}*/
                constant attribute type :>> type : Profile::DataTypes::EventEnum :> type default type::CODE;
            }
            part def CompositionState :> Event {
                doc /* {{def(EventEnum::COMPOSITION_STATE)}}*/
                constant attribute type :>> type : Profile::DataTypes::EventEnum :> type default type::COMPOSITION_STATE;
                constant attribute subType :>> subType : Profile::DataTypes::DataItemSubTypeEnum :> subType;
            }
            part def 'CompositionState.Action' :> CompositionState {
                doc /* indication of the operating state of a mechanism.*/
                constant attribute subType :>> ActiveAxes::subType : Profile::DataTypes::DataItemSubTypeEnum :> ActiveAxes::subType default "ACTION";
                attribute result [0..1] :>> result : Profile::DataTypes::CompositionStateActionEnum;
            }
            part def 'CompositionState.Lateral' :> CompositionState {
                doc /* indication of the position of a mechanism that may move in a lateral direction.   */
                constant attribute subType :>> ActiveAxes::subType : Profile::DataTypes::DataItemSubTypeEnum :> ActiveAxes::subType default "LATERAL";
                attribute result [0..1] :>> result : Profile::DataTypes::CompositionStateLateralEnum;
            }
            part def 'CompositionState.Motion' :> CompositionState {
                doc /* indication of the open or closed state of a mechanism.
                 */
                constant attribute subType :>> ActiveAxes::subType : Profile::DataTypes::DataItemSubTypeEnum :> ActiveAxes::subType default "MOTION";
                attribute result [0..1] :>> result : Profile::DataTypes::CompositionStateMotionEnum;
            }
            part def 'CompositionState.Switched' :> CompositionState {
                doc /* indication of the activation state of a mechanism.*/
                constant attribute subType :>> ActiveAxes::subType : Profile::DataTypes::DataItemSubTypeEnum :> ActiveAxes::subType default "SWITCHED";
                attribute result [0..1] :>> result : Profile::DataTypes::CompositionStateSwitchedEnum;
            }
            part def 'CompositionState.Vertical' :> CompositionState {
                doc /* indication of the position of a mechanism that may move in a vertical direction.*/
                constant attribute subType :>> ActiveAxes::subType : Profile::DataTypes::DataItemSubTypeEnum :> ActiveAxes::subType default "VERTICAL";
                attribute result [0..1] :>> result : Profile::DataTypes::CompositionStateVerticalEnum;
            }
            part def ControllerMode :> Event {
                doc /* {{def(EventEnum::CONTROLLER_MODE)}}*/
                attribute result [0..1] :>> result : Profile::DataTypes::ControllerModeEnum :> result;
                constant attribute type :>> type : Profile::DataTypes::EventEnum :> type default type::CONTROLLER_MODE;
            }
            part def ControllerModeOverride :> Event {
                doc /* {{def(EventEnum::CONTROLLER_MODE_OVERRIDE)}}*/
                constant attribute type :>> ActiveAxes::type : Profile::DataTypes::EventEnum :> ActiveAxes::type default type::CONTROLLER_MODE_OVERRIDE;
                attribute result [0..1] :>> result : Profile::DataTypes::ControllerModeOverrideEnum :> result;
                constant attribute subType :>> subType : Profile::DataTypes::DataItemSubTypeEnum :> subType;
            }
            part def 'ControllerModeOverride.DryRun' :> ControllerModeOverride {
                doc 
                /* setting or operator selection used to execute a test mode to confirm the execution of machine functions. 
                 *
                 * When `DRY_RUN` is `ON`, the equipment performs all of its normal functions, except no part or product is produced.  If the equipment has a spindle, spindle operation is suspended.*/
                constant attribute subType :>> ActiveAxes::subType : Profile::DataTypes::DataItemSubTypeEnum :> ActiveAxes::subType default "DRY_RUN";
            }
            part def 'ControllerModeOverride.SingleBlock' :> ControllerModeOverride {
                doc 
                /* setting or operator selection that changes the behavior of the controller on a piece of equipment. 
                 *
                 * Program execution is paused after each block of code is executed when `SINGLE_BLOCK` is `ON`.   
                 *
                 * When `SINGLE_BLOCK` is `ON`, {{block(Execution)}} **MUST** change to `INTERRUPTED` after completion of each block of code. */
                constant attribute subType :>> ActiveAxes::subType : Profile::DataTypes::DataItemSubTypeEnum :> ActiveAxes::subType default "SINGLE_BLOCK";
            }
            part def 'ControllerModeOverride.MachineAxisLock' :> ControllerModeOverride {
                doc 
                /* setting or operator selection that changes the behavior of the controller on a piece of equipment. 
                 *  
                 * When `MACHINE_AXIS_LOCK` is `ON`, program execution continues normally, but no equipment motion occurs.*/
                constant attribute subType :>> ActiveAxes::subType : Profile::DataTypes::DataItemSubTypeEnum :> ActiveAxes::subType default "MACHINE_AXIS_LOCK";
            }
            part def 'ControllerModeOverride.OptionalStop' :> ControllerModeOverride {
                doc 
                /* setting or operator selection that changes the behavior of the controller on a piece of equipment. 
                 *
                 * The program execution is stopped after a specific program block is executed when `OPTIONAL_STOP` is `ON`.    
                 *
                 * In the case of a G-Code program, a program block containing a M01 code designates the command for an `OPTIONAL_STOP`. 
                 *
                 * {{block(Execution)}} **MUST** change to `OPTIONAL_STOP` after a program block specifying an optional stop is executed and the {{block(ControllerModeOverride)}} `OPTIONAL_STOP` selection is `ON`.*/
                constant attribute subType :>> ActiveAxes::subType : Profile::DataTypes::DataItemSubTypeEnum :> ActiveAxes::subType default "OPTIONAL_STOP";
            }
            part def 'ControllerModeOverride.ToolChangeStop' :> ControllerModeOverride {
                doc 
                /* setting or operator selection that changes the behavior of the controller on a piece of equipment.  
                 *
                 * Program execution is paused when a command is executed requesting a cutting tool to be changed. 
                 *
                 * {{block(Execution)}} **MUST** change to `INTERRUPTED` after completion of the command requesting a cutting tool to be changed and `TOOL_CHANGE_STOP` is `ON`.*/
                constant attribute subType :>> ActiveAxes::subType : Profile::DataTypes::DataItemSubTypeEnum :> ActiveAxes::subType default "TOOL_CHANGE_STOP";
            }
            part def CoupledAxes :> Event {
                doc /* {{def(EventEnum::COUPLED_AXES)}}*/
                attribute result [0..*] :>> result : Profile::DataTypes::string;
                constant attribute type :>> type : Profile::DataTypes::EventEnum :> type default type::COUPLED_AXES;
            }
            part def DateCode :> Event {
                doc /* {{def(EventEnum::DATE_CODE)}}*/
                constant attribute type :>> type : Profile::DataTypes::EventEnum :> type default type::DATE_CODE;
                attribute result [0..1] :>> result : Profile::DataTypes::datetime :> result;
            }
            part def 'DateCode.Manufacture' :> DateCode {
                doc /* time and date code relating to the production of a material or other physical item.*/
                constant attribute subType :>> subType : Profile::DataTypes::DataItemSubTypeEnum :> subType default "MANUFACTURE";
            }
            part def 'DateCode.Expiration' :> DateCode {
                doc /* time and date code relating to the expiration or end of useful life for a material or other physical item.*/
                constant attribute subType :>> subType : Profile::DataTypes::DataItemSubTypeEnum :> subType default "EXPIRATION";
            }
            part def 'DateCode.FirstUse' :> DateCode {
                doc /* time and date code relating the first use of a material or other physical item.*/
                constant attribute subType :>> subType : Profile::DataTypes::DataItemSubTypeEnum :> subType default "FIRST_USE";
            }
            part def DeviceUuid :> Event {
                doc /* {{def(EventEnum::DEVICE_UUID)}}*/
                constant attribute type :>> type : Profile::DataTypes::EventEnum :> type default type::DEVICE_UUID;
            }
            part def Direction :> Event {
                doc /* {{def(EventEnum::DIRECTION)}}*/
                constant attribute type :>> type : Profile::DataTypes::EventEnum :> type default type::DIRECTION;
                attribute result [0..1] :>> result : Profile::DataTypes::DirectionEnum :> result;
                constant attribute subType :>> subType : Profile::DataTypes::DataItemSubTypeEnum :> subType;
            }
            part def 'Direction.Rotary' :> Direction {
                doc /* rotational direction of a rotary motion using the right hand rule convention.*/
                constant attribute subType :>> ActiveAxes::subType : Profile::DataTypes::DataItemSubTypeEnum :> ActiveAxes::subType default "ROTARY";
                attribute result [0..1] :>> ActiveAxes::result : Profile::DataTypes::DirectionRotaryEnum :> ActiveAxes::result;
            }
            part def 'Direction.Linear' :> Direction {
                doc /* direction of motion of a linear motion.*/
                constant attribute subType :>> ActiveAxes::subType : Profile::DataTypes::DataItemSubTypeEnum :> ActiveAxes::subType default "LINEAR";
                attribute result [0..1] :>> ActiveAxes::result : Profile::DataTypes::DirectionLinearEnum :> ActiveAxes::result;
            }
            part def DoorState :> Event {
                doc /* {{def(EventEnum::DOOR_STATE)}}*/
                attribute result [0..1] :>> result : Profile::DataTypes::DoorStateEnum :> result;
                constant attribute type :>> type : Profile::DataTypes::EventEnum :> type default type::DOOR_STATE;
            }
            part def EmergencyStop :> Event {
                doc /* {{def(EventEnum::EMERGENCY_STOP)}}*/
                attribute result [0..1] :>> result : Profile::DataTypes::EmergencyStopEnum :> result;
                constant attribute type :>> type : Profile::DataTypes::EventEnum :> type default type::EMERGENCY_STOP;
            }
            part def EndOfBar :> Event {
                doc /* {{def(EventEnum::END_OF_BAR)}}*/
                attribute result [0..1] :>> result : Profile::DataTypes::EndOfBarEnum :> result;
                constant attribute type :>> type : Profile::DataTypes::EventEnum :> type default type::END_OF_BAR;
                constant attribute subType :>> subType : Profile::DataTypes::DataItemSubTypeEnum :> subType default subType::PRIMARY;
            }
            part def 'EndOfBar.Primary' :> EndOfBar {
                doc 
                /* specific applications **MAY** reference one or more locations on a piece of bar stock as the indication for the {{block(EndOfBar)}}. 
                 *
                 * The main or most important location **MUST** be designated as the {{block(PRIMARY)}} indication for the {{block(EndOfBar)}}.
                 *
                 * If no {{block(subType)}} is specified, {{block(PRIMARY)}} **MUST** be the default {{block(EndOfBar)}} indication.*/
                constant attribute subType :>> ActiveAxes::subType : Profile::DataTypes::DataItemSubTypeEnum :> ActiveAxes::subType default "PRIMARY";
            }
            part def 'EndOfBar.Auxiliary' :> EndOfBar {
                doc /* when multiple locations on a piece of bar stock are referenced as the indication for the {{block(EndOfBar)}}, the additional location(s) **MUST** be designated as `AUXILIARY` indication(s) for the {{block(EndOfBar)}}.  */
                constant attribute subType :>> ActiveAxes::subType : Profile::DataTypes::DataItemSubTypeEnum :> ActiveAxes::subType default "AUXILIARY";
            }
            part def EquipmentMode :> Event {
                doc /* {{def(EventEnum::EQUIPMENT_MODE)}}*/
                attribute result [0..1] :>> result : Profile::DataTypes::EquipmentModeEnum :> result;
                constant attribute type :>> type : Profile::DataTypes::EventEnum :> type default type::EQUIPMENT_MODE;
                constant attribute subType :>> subType : Profile::DataTypes::DataItemSubTypeEnum :> subType;
            }
            part def 'EquipmentMode.Loaded' :> EquipmentMode {
                doc 
                /* indication that the sub-parts of a piece of equipment are under load.
                 *
                 * Example: For traditional machine tools, this is an indication that the cutting tool is assumed to be engaged with the part.*/
                constant attribute subType :>> ActiveAxes::subType : Profile::DataTypes::DataItemSubTypeEnum :> ActiveAxes::subType default "LOADED";
            }
            part def 'EquipmentMode.Working' :> EquipmentMode {
                doc 
                /* indication that a piece of equipment is performing any activity, the equipment is active and performing a function under load or not.
                 *
                 * Example: For traditional machine tools, this includes when the piece of equipment is `LOADED`, making rapid moves, executing a tool change, etc.*/
                constant attribute subType :>> ActiveAxes::subType : Profile::DataTypes::DataItemSubTypeEnum :> ActiveAxes::subType default "WORKING";
            }
            part def 'EquipmentMode.Operating' :> EquipmentMode {
                doc 
                /* indication that the major sub-parts of a piece of equipment are powered or performing any activity whether producing a part or product or not.
                 *
                 * Example: For traditional machine tools, this includes when the piece of equipment is `WORKING` or it is idle.*/
                constant attribute subType :>> ActiveAxes::subType : Profile::DataTypes::DataItemSubTypeEnum :> ActiveAxes::subType default "OPERATING";
            }
            part def 'EquipmentMode.Powered' :> EquipmentMode {
                doc 
                /* indication that primary power is applied to the piece of equipment and, as a minimum, the controller or logic portion of the piece of equipment is powered and functioning or components that are required to remain on are
                 * powered.
                 *
                 * Example: Heaters for an extrusion machine that required to be powered even when the equipment is turned off.*/
                constant attribute subType :>> ActiveAxes::subType : Profile::DataTypes::DataItemSubTypeEnum :> ActiveAxes::subType default "POWERED";
            }
            part def 'EquipmentMode.Delay' :> EquipmentMode {
                doc /* elapsed time of a temporary halt of action.*/
                constant attribute subType :>> ActiveAxes::subType : Profile::DataTypes::DataItemSubTypeEnum :> ActiveAxes::subType default "DELAY";
            }
            part def Execution :> Event {
                doc /* {{def(EventEnum::EXECUTION)}}*/
                attribute result [0..1] :>> result : Profile::DataTypes::ExecutionEnum :> result;
                constant attribute type :>> type : Profile::DataTypes::EventEnum :> type default type::EXECUTION;
            }
            part def FunctionalMode :> Event {
                doc /* {{def(EventEnum::FUNCTIONAL_MODE)}}*/
                attribute result [0..1] :>> result : Profile::DataTypes::FunctionalModeEnum :> result;
                constant attribute type :>> type : Profile::DataTypes::EventEnum :> type default type::FUNCTIONAL_MODE;
            }
            part def Hardness :> Event {
                doc /* {{def(EventEnum::HARDNESS)}}*/
                attribute result [0..1] :>> result : Profile::DataTypes::float;
                constant attribute type :>> type : Profile::DataTypes::EventEnum :> type default type::HARDNESS;
                constant attribute subType :>> subType : Profile::DataTypes::DataItemSubTypeEnum :> subType;
            }
            part def 'Hardness.Rockwell' :> Hardness {
                doc /* scale to measure the resistance to deformation of a surface.*/
                constant attribute subType :>> ActiveAxes::subType : Profile::DataTypes::DataItemSubTypeEnum :> ActiveAxes::subType default "ROCKWELL";
            }
            part def 'Hardness.Vickers' :> Hardness {
                doc /* scale to measure the resistance to deformation of a surface.*/
                constant attribute subType :>> ActiveAxes::subType : Profile::DataTypes::DataItemSubTypeEnum :> ActiveAxes::subType default "VICKERS";
            }
            part def 'Hardness.Shore' :> Hardness {
                doc /* scale to measure the resistance to deformation of a surface.*/
                constant attribute subType :>> ActiveAxes::subType : Profile::DataTypes::DataItemSubTypeEnum :> ActiveAxes::subType default "SHORE";
            }
            part def 'Hardness.Brinell' :> Hardness {
                doc /* scale to measure the resistance to deformation of a surface.*/
                constant attribute subType :>> ActiveAxes::subType : Profile::DataTypes::DataItemSubTypeEnum :> ActiveAxes::subType default "BRINELL";
            }
            part def 'Hardness.Leeb' :> Hardness {
                doc /* scale to measure the elasticity of a surface.*/
                constant attribute subType :>> ActiveAxes::subType : Profile::DataTypes::DataItemSubTypeEnum :> ActiveAxes::subType default "LEEB";
            }
            part def 'Hardness.Mohs' :> Hardness {
                doc /* scale to measure the resistance to scratching of a surface.*/
                constant attribute subType :>> ActiveAxes::subType : Profile::DataTypes::DataItemSubTypeEnum :> ActiveAxes::subType default "MOHS";
            }
            part def Line :> Event {
                doc /* {{def(EventEnum::LINE)}}*/
                constant attribute type :>> type : Profile::DataTypes::EventEnum :> type default type::LINE;
            }
            part def 'Line.Maximum' :> Line {
                doc /* maximum line number of the code being executed.*/
                constant attribute subType :>> subType : Profile::DataTypes::DataItemSubTypeEnum :> subType default "MAXIMUM";
            }
            part def 'Line.Minimum' :> Line {
                doc /* minimum line number of the code being executed.*/
                constant attribute subType :>> subType : Profile::DataTypes::DataItemSubTypeEnum :> subType default "MINIMUM";
            }
            part def LineLabel :> Event {
                doc /* {{def(EventEnum::LINE_LABEL)}}*/
                constant attribute type :>> type : Profile::DataTypes::EventEnum :> type default type::LINE_LABEL;
            }
            part def LineNumber :> Event {
                doc /* {{def(EventEnum::LINE_NUMBER)}}*/
                attribute result [0..1] :>> result : Profile::DataTypes::integer;
                constant attribute type :>> type : Profile::DataTypes::EventEnum :> type default type::LINE_NUMBER;
            }
            part def 'LineNumber.Absolute' :> LineNumber {
                doc /* position of a block of program code relative to the beginning of the control program.*/
                constant attribute subType :>> subType : Profile::DataTypes::DataItemSubTypeEnum :> subType default "ABSOLUTE";
            }
            part def 'LineNumber.Incremental' :> LineNumber {
                doc /* position of a block of program code relative to the occurrence of the last {{block(LineLabel)}} encountered in the control program.*/
                constant attribute subType :>> subType : Profile::DataTypes::DataItemSubTypeEnum :> subType default "INCREMENTAL";
            }
            part def Material :> Event {
                doc /* {{def(EventEnum::MATERIAL)}}*/
                constant attribute type :>> type : Profile::DataTypes::EventEnum :> type default type::MATERIAL;
            }
            part def MaterialLayer :> Event {
                doc /* {{def(EventEnum::MATERIAL_LAYER)}}*/
                attribute result [0..1] :>> result : Profile::DataTypes::integer;
                constant attribute type :>> type : Profile::DataTypes::EventEnum :> type default type::MATERIAL_LAYER;
            }
            part def 'MaterialLayer.Actual' :> MaterialLayer {
                doc /* measured or reported value of an {{term(observation)}}.*/
                constant attribute subType :>> subType : Profile::DataTypes::DataItemSubTypeEnum :> subType default "ACTUAL";
            }
            part def 'MaterialLayer.Target' :> MaterialLayer {
                doc /* goal of the operation or process.*/
                constant attribute subType :>> subType : Profile::DataTypes::DataItemSubTypeEnum :> subType default "TARGET";
            }
            part def Message :> Event {
                doc /* {{def(EventEnum::MESSAGE)}}*/
                constant attribute type :>> type : Profile::DataTypes::EventEnum :> type default type::MESSAGE;
                attribute nativeCode [0..1] : Profile::DataTypes::string {
                    doc /* control system local identification of the information being transferred.*/
                }
            }
            part def OperatorId :> Event {
                doc /* {{def(EventEnum::OPERATOR_ID)}}*/
                constant attribute type :>> type : Profile::DataTypes::EventEnum :> type default type::OPERATOR_ID;
            }
            part def PalletId :> Event {
                doc /* {{def(EventEnum::PALLET_ID)}}*/
                constant attribute type :>> type : Profile::DataTypes::EventEnum :> type default type::PALLET_ID;
            }
            part def PartCount :> Event {
                doc /* {{def(EventEnum::PART_COUNT)}}*/
                attribute result [0..1] :>> result : Profile::DataTypes::integer;
                constant attribute type :>> type : Profile::DataTypes::EventEnum :> type default type::PART_COUNT;
                constant attribute subType :>> subType : Profile::DataTypes::DataItemSubTypeEnum :> subType default subType::ALL;
            }
            part def 'PartCount.All' :> PartCount {
                doc /* accumulation of all actions, items, or activities being counted independent of the outcome.*/
                constant attribute subType :>> ActiveAxes::subType : Profile::DataTypes::DataItemSubTypeEnum :> ActiveAxes::subType default "ALL";
            }
            part def 'PartCount.Good' :> PartCount {
                doc /* accumulation of actions, items, or activities being counted that conform to specification or expectation.*/
                constant attribute subType :>> ActiveAxes::subType : Profile::DataTypes::DataItemSubTypeEnum :> ActiveAxes::subType default "GOOD";
            }
            part def 'PartCount.Bad' :> PartCount {
                doc /* accumulation of actions, items, or activities being counted that do not conform to specification or expectation.*/
                constant attribute subType :>> ActiveAxes::subType : Profile::DataTypes::DataItemSubTypeEnum :> ActiveAxes::subType default "BAD";
            }
            part def 'PartCount.Target' :> PartCount {
                doc /* goal of the operation or process.*/
                constant attribute subType :>> ActiveAxes::subType : Profile::DataTypes::DataItemSubTypeEnum :> ActiveAxes::subType default "TARGET";
            }
            part def 'PartCount.Remaining' :> PartCount {
                doc /* accumulation of actions, items, or activities yet to be counted.*/
                constant attribute subType :>> ActiveAxes::subType : Profile::DataTypes::DataItemSubTypeEnum :> ActiveAxes::subType default "REMAINING";
            }
            part def PartDetect :> Event {
                doc /* {{def(EventEnum::PART_DETECT)}}*/
                attribute result [0..1] :>> result : Profile::DataTypes::PartDetectEnum;
                constant attribute type :>> type : Profile::DataTypes::EventEnum :> type default type::PART_DETECT;
            }
            part def PartId :> Event {
                doc /* {{def(EventEnum::PART_ID)}}*/
                constant attribute type :>> type : Profile::DataTypes::EventEnum :> type default type::PART_ID;
            }
            part def PartNumber :> Event {
                doc /* {{def(EventEnum::PART_NUMBER)}}*/
                constant attribute type :>> type : Profile::DataTypes::EventEnum :> type default type::PART_NUMBER;
            }
            part def PathFeedrateOverride :> Event {
                doc /* {{def(EventEnum::PATH_FEEDRATE_OVERRIDE)}}*/
                attribute result [0..1] :>> result : Profile::DataTypes::float;
                constant attribute type :>> type : Profile::DataTypes::EventEnum :> type default type::PATH_FEEDRATE_OVERRIDE;
            }
            part def 'PathFeedrateOverride.Jog' :> PathFeedrateOverride {
                doc 
                /* relating to momentary activation of a function or a movement.
                 *
                 * **DEPRECATION WARNING**: May be deprecated in the future.*/
                constant attribute subType :>> subType : Profile::DataTypes::DataItemSubTypeEnum :> subType default "JOG";
            }
            part def 'PathFeedrateOverride.Programmed' :> PathFeedrateOverride {
                doc /* directive value without offsets and adjustments.*/
                constant attribute subType :>> subType : Profile::DataTypes::DataItemSubTypeEnum :> subType default "PROGRAMMED";
            }
            part def 'PathFeedrateOverride.Rapid' :> PathFeedrateOverride {
                doc /* performing an operation faster or in less time than nominal rate.*/
                constant attribute subType :>> subType : Profile::DataTypes::DataItemSubTypeEnum :> subType default "RAPID";
            }
            part def PathMode :> Event {
                doc /* {{def(EventEnum::PATH_MODE)}}*/
                attribute result [0..1] :>> result : Profile::DataTypes::PathModeEnum :> result default result::INDEPENDENT;
                constant attribute type :>> type : Profile::DataTypes::EventEnum :> type default type::PATH_MODE;
            }
            part def PowerState :> Event {
                doc /* {{def(EventEnum::POWER_STATE)}}*/
                attribute result [0..1] :>> result : Profile::DataTypes::PowerStateEnum :> result;
                constant attribute type :>> type : Profile::DataTypes::EventEnum :> type default type::POWER_STATE;
            }
            part def 'PowerState.Line' :> PowerState {
                doc /* state of the power source for the entity.*/
                constant attribute subType :>> subType : Profile::DataTypes::DataItemSubTypeEnum :> subType default "LINE";
            }
            part def 'PowerState.Control' :> PowerState {
                doc /* state of the enabling signal or control logic that enables or disables the function or operation of the entity.*/
                constant attribute subType :>> subType : Profile::DataTypes::DataItemSubTypeEnum :> subType default "CONTROL";
            }
            part def PowerStatus :> Event {
                doc /* {{def(EventEnum::POWER_STATUS)}}*/
                constant attribute type :>> type : Profile::DataTypes::EventEnum :> type default type::POWER_STATUS;
                attribute result [0..1] :>> result : Profile::DataTypes::PowerStatusEnum :> result;
            }
            part def ProcessTime :> Event {
                doc /* {{def(EventEnum::PROCESS_TIME)}}*/
                constant attribute type :>> type : Profile::DataTypes::EventEnum :> type default type::PROCESS_TIME;
                constant attribute subType :>> subType : Profile::DataTypes::DataItemSubTypeEnum :> subType;
            }
            part def 'ProcessTime.Start' :> ProcessTime {
                doc /* boundary when an activity or an event commences.*/
                constant attribute subType :>> ActiveAxes::subType : Profile::DataTypes::DataItemSubTypeEnum :> ActiveAxes::subType default "START";
            }
            part def 'ProcessTime.Complete' :> ProcessTime {
                doc /* time and date associated with the completion of an activity or event.*/
                constant attribute subType :>> ActiveAxes::subType : Profile::DataTypes::DataItemSubTypeEnum :> ActiveAxes::subType default "COMPLETE";
            }
            part def 'ProcessTime.TargetCompletion' :> ProcessTime {
                doc /* projected time and date associated with the end or completion of an activity or event.*/
                constant attribute subType :>> ActiveAxes::subType : Profile::DataTypes::DataItemSubTypeEnum :> ActiveAxes::subType default "TARGET_COMPLETION";
            }
            part def Program :> Event {
                doc /* {{def(EventEnum::PROGRAM)}}*/
                constant attribute type :>> type : Profile::DataTypes::EventEnum :> type default type::PROGRAM;
            }
            part def ProgramComment :> Event {
                doc /* {{def(EventEnum::PROGRAM_COMMENT)}}*/
                constant attribute type :>> type : Profile::DataTypes::EventEnum :> type default type::PROGRAM_COMMENT;
            }
            part def ProgramEdit :> Event {
                doc /* {{def(EventEnum::PROGRAM_EDIT)}}*/
                attribute result [0..1] :>> result : Profile::DataTypes::ProgramEditEnum :> result;
                constant attribute type :>> type : Profile::DataTypes::EventEnum :> type default type::PROGRAM_EDIT;
            }
            part def ProgramEditName :> Event {
                doc /* {{def(EventEnum::PROGRAM_EDIT_NAME)}}*/
                constant attribute type :>> type : Profile::DataTypes::EventEnum :> type default type::PROGRAM_EDIT_NAME;
            }
            part def ProgramHeader :> Event {
                doc /* {{def(EventEnum::PROGRAM_HEADER)}}*/
                constant attribute type :>> type : Profile::DataTypes::EventEnum :> type default type::PROGRAM_HEADER;
                constant attribute subType :>> subType : Profile::DataTypes::DataItemSubTypeEnum :> subType default subType::MAIN;
            }
            part def ProgramLocation :> Event {
                doc /* {{def(EventEnum::PROGRAM_LOCATION)}}*/
                constant attribute type :>> type : Profile::DataTypes::EventEnum :> type default type::PROGRAM_LOCATION;
            }
            part def 'ProgramLocation.Schedule' :> ProgramLocation {
                doc /* identity of a control program that is used to specify the order of execution of other programs.*/
                constant attribute subType :>> subType : Profile::DataTypes::DataItemSubTypeEnum :> subType default "SCHEDULE";
            }
            part def 'ProgramLocation.Main' :> ProgramLocation {
                doc 
                /* identity of the primary logic or motion program currently being executed. 
                 *
                 * It is the starting nest level in a call structure and may contain calls to sub programs.*/
                constant attribute subType :>> subType : Profile::DataTypes::DataItemSubTypeEnum :> subType default "MAIN";
            }
            part def 'ProgramLocation.Active' :> ProgramLocation {
                doc /* identity of the logic or motion program currently executing.*/
                constant attribute subType :>> subType : Profile::DataTypes::DataItemSubTypeEnum :> subType default "ACTIVE";
            }
            part def ProgramLocationType :> Event {
                doc /* {{def(EventEnum::PROGRAM_LOCATION_TYPE)}}*/
                constant attribute type :>> type : Profile::DataTypes::EventEnum :> type default type::PROGRAM_LOCATION_TYPE;
                attribute result [0..1] :>> result : Profile::DataTypes::ProgramLocationTypeEnum :> result;
            }
            part def 'ProgramLocationType.Schedule' :> ProgramLocationType {
                doc /* identity of a control program that is used to specify the order of execution of other programs.*/
                constant attribute subType :>> subType : Profile::DataTypes::DataItemSubTypeEnum :> subType default "SCHEDULE";
            }
            part def 'ProgramLocationType.Main' :> ProgramLocationType {
                doc 
                /* identity of the primary logic or motion program currently being executed. 
                 *
                 * It is the starting nest level in a call structure and may contain calls to sub programs.*/
                constant attribute subType :>> subType : Profile::DataTypes::DataItemSubTypeEnum :> subType default "MAIN";
            }
            part def 'ProgramLocationType.Active' :> ProgramLocationType {
                doc /* identity of the logic or motion program currently executing.*/
                constant attribute subType :>> subType : Profile::DataTypes::DataItemSubTypeEnum :> subType default "ACTIVE";
            }
            part def ProgramNestLevel :> Event {
                doc 
                /* {{def(EventEnum::PROGRAM_NEST_LEVEL)}}
                 *
                 * If an initial value is not defined, the nesting level associated with the highest or initial nesting level of the program **MUST** default to zero (0).
                 */
                attribute result [0..1] :>> result : Profile::DataTypes::integer;
                constant attribute type :>> type : Profile::DataTypes::EventEnum :> type default type::PROGRAM_NEST_LEVEL;
            }
            part def RotaryMode :> Event {
                doc /* {{def(EventEnum::ROTARY_MODE)}}*/
                attribute result [0..1] :>> result : Profile::DataTypes::RotaryModeEnum :> result;
                constant attribute type :>> type : Profile::DataTypes::EventEnum :> type default type::ROTARY_MODE;
            }
            part def RotaryVelocityOverride :> Event {
                doc 
                /* {{def(EventEnum::ROTARY_VELOCITY_OVERRIDE)}}
                 *
                 * This command represents a percentage change to the velocity calculated by a logic or motion program or set by a switch for a {{block(Rotary)}} type axis.*/
                attribute result [0..1] :>> result : Profile::DataTypes::float;
                constant attribute type :>> type : Profile::DataTypes::EventEnum :> type default type::ROTARY_VELOCITY_OVERRIDE;
            }
            part def SerialNumber :> Event {
                doc /* {{def(EventEnum::SERIAL_NUMBER)}}*/
                constant attribute type :>> type : Profile::DataTypes::EventEnum :> type default type::SERIAL_NUMBER;
            }
            part def SpindleInterlock :> Event {
                doc /* {{def(EventEnum::SPINDLE_INTERLOCK)}}*/
                attribute result [0..1] :>> result : Profile::DataTypes::SpindleInterlockEnum :> result;
                constant attribute type :>> type : Profile::DataTypes::EventEnum :> type default type::SPINDLE_INTERLOCK;
            }
            part def ToolAssetId :> Event {
                doc /* {{def(EventEnum::TOOL_ASSET_ID)}}*/
                constant attribute type :>> type : Profile::DataTypes::EventEnum :> type default type::TOOL_ASSET_ID;
            }
            part def ToolGroup :> Event {
                doc /* {{def(EventEnum::TOOL_GROUP)}}*/
                constant attribute type :>> type : Profile::DataTypes::EventEnum :> type default type::TOOL_GROUP;
            }
            part def ToolId :> Event {
                doc /* {{def(EventEnum::TOOL_ID)}}*/
                constant attribute type :>> type : Profile::DataTypes::EventEnum :> type default type::TOOL_ID;
            }
            part def ToolNumber :> Event {
                doc /* {{def(EventEnum::TOOL_NUMBER)}}*/
                constant attribute type :>> type : Profile::DataTypes::EventEnum :> type default type::TOOL_NUMBER;
            }
            part def ToolOffset :> Event {
                doc /* {{def(EventEnum::TOOL_OFFSET)}}*/
                attribute result [0..1] :>> result : Profile::DataTypes::float;
                constant attribute type :>> type : Profile::DataTypes::EventEnum :> type default type::TOOL_OFFSET;
                constant attribute subType :>> subType : Profile::DataTypes::DataItemSubTypeEnum :> subType;
            }
            part def 'ToolOffset.Radial' :> ToolOffset {
                doc /* reference to a radial type tool offset variable.*/
                constant attribute subType :>> ActiveAxes::subType : Profile::DataTypes::DataItemSubTypeEnum :> ActiveAxes::subType default "RADIAL";
            }
            part def 'ToolOffset.Length' :> ToolOffset {
                doc /* reference to a length type tool offset variable.*/
                constant attribute subType :>> ActiveAxes::subType : Profile::DataTypes::DataItemSubTypeEnum :> ActiveAxes::subType default "LENGTH";
            }
            part def User :> Event {
                doc /* {{def(EventEnum::USER)}}*/
                constant attribute type :>> type : Profile::DataTypes::EventEnum :> type default type::USER;
                constant attribute subType :>> subType : Profile::DataTypes::DataItemSubTypeEnum :> subType;
            }
            part def 'User.Operator' :> User {
                doc /* identifier of the person currently responsible for operating the piece of equipment.*/
                constant attribute subType :>> ActiveAxes::subType : Profile::DataTypes::DataItemSubTypeEnum :> ActiveAxes::subType default "OPERATOR";
            }
            part def 'User.Maintenance' :> User {
                doc /* identifier of the person currently responsible for performing maintenance on the piece of equipment.*/
                constant attribute subType :>> ActiveAxes::subType : Profile::DataTypes::DataItemSubTypeEnum :> ActiveAxes::subType default "MAINTENANCE";
            }
            part def 'User.SetUp' :> User {
                doc /* identifier of the person currently responsible for preparing a piece of equipment for production or restoring the piece of equipment to a neutral state after production.*/
                constant attribute subType :>> ActiveAxes::subType : Profile::DataTypes::DataItemSubTypeEnum :> ActiveAxes::subType default "SET_UP";
            }
            part def Variable :> Event {
                doc /* {{def(EventEnum::VARIABLE)}}*/
                constant attribute type :>> type : Profile::DataTypes::EventEnum :> type default type::VARIABLE;
            }
            part def WaitState :> Event {
                doc 
                /* {{def(EventEnum::WAIT_STATE)}}
                 *
                 * When {{property(Execution::result)}} is not `WAIT`, {{property(Observation::isUnavailable)}} of {{block(WaitState)}} **MUST** be `true`.*/
                attribute result [0..1] :>> result : Profile::DataTypes::WaitStateEnum;
                constant attribute type :>> type : Profile::DataTypes::EventEnum :> type default type::WAIT_STATE;
            }
            part def Wire :> Event {
                doc /* {{def(EventEnum::WIRE)}}*/
                constant attribute type :>> type : Profile::DataTypes::EventEnum :> type default type::WIRE;
            }
            part def WorkholdingId :> Event {
                doc /* {{def(EventEnum::WORKHOLDING_ID)}}*/
                constant attribute type :>> type : Profile::DataTypes::EventEnum :> type default type::WORKHOLDING_ID;
            }
            part def WorkOffset :> Event {
                doc /* {{def(EventEnum::WORK_OFFSET)}}*/
                constant attribute type :>> type : Profile::DataTypes::EventEnum :> type default type::WORK_OFFSET;
            }
            part def 'ProgramHeader.Main' :> ProgramHeader {
                doc 
                /* identity of the primary logic or motion program currently being executed. 
                 *
                 * It is the starting nest level in a call structure and may contain calls to sub programs.*/
                constant attribute subType :>> ActiveAxes::subType : Profile::DataTypes::DataItemSubTypeEnum :> ActiveAxes::subType default "MAIN";
            }
            part def 'ProgramHeader.Schedule' :> ProgramHeader {
                doc /* identity of a control program that is used to specify the order of execution of other programs.*/
                constant attribute subType :>> ActiveAxes::subType : Profile::DataTypes::DataItemSubTypeEnum :> ActiveAxes::subType default "SCHEDULE";
            }
            part def 'ProgramHeader.Active' :> ProgramHeader {
                doc /* identity of the logic or motion program currently executing.*/
                constant attribute subType :>> ActiveAxes::subType : Profile::DataTypes::DataItemSubTypeEnum :> ActiveAxes::subType default "ACTIVE";
            }
            part def OperatingSystem :> Event {
                doc /* {{def(EventEnum::OPERATING_SYSTEM)}}*/
                constant attribute type :>> type : Profile::DataTypes::EventEnum :> type default type::OPERATING_SYSTEM;
                constant attribute subType :>> subType : Profile::DataTypes::DataItemSubTypeEnum :> subType;
            }
            part def 'OperatingSystem.License' :> OperatingSystem {
                doc /* license code to validate or activate the hardware or software.*/
                constant attribute subType :>> ActiveAxes::subType : Profile::DataTypes::DataItemSubTypeEnum :> ActiveAxes::subType default subType::LICENSE;
            }
            part def 'OperatingSystem.Version' :> OperatingSystem {
                doc /* version of the hardware or software.*/
                constant attribute subType :>> ActiveAxes::subType : Profile::DataTypes::DataItemSubTypeEnum :> ActiveAxes::subType default subType::VERSION;
            }
            part def 'OperatingSystem.ReleaseDate' :> OperatingSystem {
                doc /* date the hardware or software was released for general use. */
                constant attribute subType :>> ActiveAxes::subType : Profile::DataTypes::DataItemSubTypeEnum :> ActiveAxes::subType default subType::RELEASE_DATE;
                attribute result [0..1] :>> result : Profile::DataTypes::datetime :> result;
            }
            part def 'OperatingSystem.InstallDate' :> OperatingSystem {
                doc /* date the hardware or software was installed.*/
                constant attribute subType :>> ActiveAxes::subType : Profile::DataTypes::DataItemSubTypeEnum :> ActiveAxes::subType default subType::INSTALL_DATE;
                attribute result [0..1] :>> result : Profile::DataTypes::datetime :> result;
            }
            part def 'OperatingSystem.Manufacturer' :> OperatingSystem {
                doc /* corporate identity for the maker of the hardware or software. */
                constant attribute subType :>> ActiveAxes::subType : Profile::DataTypes::DataItemSubTypeEnum :> ActiveAxes::subType default subType::MANUFACTURER;
            }
            part def 'Firmware.Version' :> Firmware {
                doc /* version of the hardware or software.*/
                constant attribute subType :>> ActiveAxes::subType : Profile::DataTypes::DataItemSubTypeEnum :> ActiveAxes::subType default subType::VERSION;
            }
            part def 'Firmware.ReleaseDate' :> Firmware {
                doc /* date the hardware or software was released for general use. */
                constant attribute subType :>> ActiveAxes::subType : Profile::DataTypes::DataItemSubTypeEnum :> ActiveAxes::subType default subType::RELEASE_DATE;
                attribute result [0..1] :>> result : Profile::DataTypes::datetime :> result;
            }
            part def Firmware :> Event {
                doc /* {{def(EventEnum::FIRMWARE)}}*/
                constant attribute type :>> type : Profile::DataTypes::EventEnum :> type default type::FIRMWARE;
                constant attribute subType :>> subType : Profile::DataTypes::DataItemSubTypeEnum :> subType;
            }
            part def 'Firmware.Manufacturer' :> Firmware {
                doc /* corporate identity for the maker of the hardware or software. */
                constant attribute subType :>> ActiveAxes::subType : Profile::DataTypes::DataItemSubTypeEnum :> ActiveAxes::subType default subType::MANUFACTURER;
            }
            part def 'Firmware.License' :> Firmware {
                doc /* license code to validate or activate the hardware or software.*/
                constant attribute subType :>> ActiveAxes::subType : Profile::DataTypes::DataItemSubTypeEnum :> ActiveAxes::subType default subType::LICENSE;
            }
            part def 'Firmware.InstallDate' :> Firmware {
                doc /* date the hardware or software was installed.*/
                constant attribute subType :>> ActiveAxes::subType : Profile::DataTypes::DataItemSubTypeEnum :> ActiveAxes::subType default subType::INSTALL_DATE;
                attribute result [0..1] :>> result : Profile::DataTypes::datetime :> result;
            }
            part def 'Application.Version' :> Application {
                doc /* version of the hardware or software.*/
                constant attribute subType :>> ActiveAxes::subType : Profile::DataTypes::DataItemSubTypeEnum :> ActiveAxes::subType default subType::VERSION;
            }
            part def 'Application.ReleaseDate' :> Application {
                doc /* date the hardware or software was released for general use. */
                constant attribute subType :>> ActiveAxes::subType : Profile::DataTypes::DataItemSubTypeEnum :> ActiveAxes::subType default subType::RELEASE_DATE;
                attribute result [0..1] :>> result : Profile::DataTypes::datetime :> result;
            }
            part def Application :> Event {
                doc /* {{def(EventEnum::APPLICATION)}}*/
                constant attribute type :>> type : Profile::DataTypes::EventEnum :> type default type::APPLICATION;
                constant attribute subType :>> subType : Profile::DataTypes::DataItemSubTypeEnum :> subType;
            }
            part def 'Application.Manufacturer' :> Application {
                doc /* corporate identity for the maker of the hardware or software. */
                constant attribute subType :>> ActiveAxes::subType : Profile::DataTypes::DataItemSubTypeEnum :> ActiveAxes::subType default subType::MANUFACTURER;
            }
            part def 'Application.License' :> Application {
                doc /* license code to validate or activate the hardware or software.*/
                constant attribute subType :>> ActiveAxes::subType : Profile::DataTypes::DataItemSubTypeEnum :> ActiveAxes::subType default subType::LICENSE;
            }
            part def 'Application.InstallDate' :> Application {
                doc /* date the hardware or software was installed.*/
                constant attribute subType :>> ActiveAxes::subType : Profile::DataTypes::DataItemSubTypeEnum :> ActiveAxes::subType default subType::INSTALL_DATE;
                attribute result [0..1] :>> result : Profile::DataTypes::datetime :> result;
            }
            part def 'Library.Version' :> Library {
                doc /* version of the hardware or software.*/
                constant attribute subType :>> ActiveAxes::subType : Profile::DataTypes::DataItemSubTypeEnum :> ActiveAxes::subType default subType::VERSION;
            }
            part def 'Library.ReleaseDate' :> Library {
                doc /* date the hardware or software was released for general use. */
                constant attribute subType :>> ActiveAxes::subType : Profile::DataTypes::DataItemSubTypeEnum :> ActiveAxes::subType default subType::RELEASE_DATE;
                attribute result [0..1] :>> result : Profile::DataTypes::datetime :> result;
            }
            part def Library :> Event {
                doc /* {{def(EventEnum::LIBRARY)}}*/
                constant attribute type :>> type : Profile::DataTypes::EventEnum :> type default type::LIBRARY;
                constant attribute subType :>> subType : Profile::DataTypes::DataItemSubTypeEnum :> subType;
            }
            part def 'Library.Manufacturer' :> Library {
                doc /* corporate identity for the maker of the hardware or software. */
                constant attribute subType :>> ActiveAxes::subType : Profile::DataTypes::DataItemSubTypeEnum :> ActiveAxes::subType default subType::MANUFACTURER;
            }
            part def 'Library.License' :> Library {
                doc /* license code to validate or activate the hardware or software.*/
                constant attribute subType :>> ActiveAxes::subType : Profile::DataTypes::DataItemSubTypeEnum :> ActiveAxes::subType default subType::LICENSE;
            }
            part def 'Library.InstallDate' :> Library {
                doc /* date the hardware or software was installed.*/
                constant attribute subType :>> ActiveAxes::subType : Profile::DataTypes::DataItemSubTypeEnum :> ActiveAxes::subType default subType::INSTALL_DATE;
                attribute result [0..1] :>> result : Profile::DataTypes::datetime :> result;
            }
            part def 'Hardware.Version' :> Hardware {
                doc /* version of the hardware or software.*/
                constant attribute subType :>> ActiveAxes::subType : Profile::DataTypes::DataItemSubTypeEnum :> ActiveAxes::subType default subType::VERSION;
            }
            part def 'Hardware.ReleaseDate' :> Hardware {
                doc /* date the hardware or software was released for general use. */
                constant attribute subType :>> ActiveAxes::subType : Profile::DataTypes::DataItemSubTypeEnum :> ActiveAxes::subType default subType::RELEASE_DATE;
                attribute result [0..1] :>> result : Profile::DataTypes::datetime :> result;
            }
            part def Hardware :> Event {
                doc /* {{def(EventEnum::HARDWARE)}}*/
                constant attribute type :>> type : Profile::DataTypes::EventEnum :> type default type::HARDWARE;
                constant attribute subType :>> subType : Profile::DataTypes::DataItemSubTypeEnum :> subType;
            }
            part def 'Hardware.Manufacturer' :> Hardware {
                doc /* corporate identity for the maker of the hardware or software. */
                constant attribute subType :>> ActiveAxes::subType : Profile::DataTypes::DataItemSubTypeEnum :> ActiveAxes::subType default subType::MANUFACTURER;
            }
            part def 'Hardware.License' :> Hardware {
                doc /* license code to validate or activate the hardware or software.*/
                constant attribute subType :>> ActiveAxes::subType : Profile::DataTypes::DataItemSubTypeEnum :> ActiveAxes::subType default subType::LICENSE;
            }
            part def 'Hardware.InstallDate' :> Hardware {
                doc /* date the hardware or software was installed.*/
                constant attribute subType :>> ActiveAxes::subType : Profile::DataTypes::DataItemSubTypeEnum :> ActiveAxes::subType default subType::INSTALL_DATE;
                attribute result [0..1] :>> result : Profile::DataTypes::datetime :> result;
            }
            part def Network :> Event {
                doc /* {{def(EventEnum::NETWORK)}}*/
                constant attribute type :>> type : Profile::DataTypes::EventEnum :> type default type::NETWORK;
                constant attribute subType :>> subType : Profile::DataTypes::DataItemSubTypeEnum :> subType;
            }
            part def 'Network.IPv4Address' :> Network {
                doc /* IPV4 network address of the component.*/
                constant attribute subType :>> ActiveAxes::subType : Profile::DataTypes::DataItemSubTypeEnum :> ActiveAxes::subType default subType::IPV4_ADDRESS;
            }
            part def 'Network.IPv6Address' :> Network {
                doc /* IPV6 network address of the component.*/
                constant attribute subType :>> ActiveAxes::subType : Profile::DataTypes::DataItemSubTypeEnum :> ActiveAxes::subType default subType::IPV6_ADDRESS;
            }
            part def 'Network.Gateway' :> Network {
                doc /* Gateway for the component network.*/
                constant attribute subType :>> ActiveAxes::subType : Profile::DataTypes::DataItemSubTypeEnum :> ActiveAxes::subType default subType::GATEWAY;
            }
            part def 'Network.SubnetMask' :> Network {
                doc /* SubNet mask for the component network.*/
                constant attribute subType :>> ActiveAxes::subType : Profile::DataTypes::DataItemSubTypeEnum :> ActiveAxes::subType default subType::SUBNET_MASK;
            }
            part def 'Network.VLanId' :> Network {
                doc /* layer2 Virtual Local Network (VLAN) ID for the component network.*/
                constant attribute subType :>> ActiveAxes::subType : Profile::DataTypes::DataItemSubTypeEnum :> ActiveAxes::subType default subType::VLAN_ID;
            }
            part def 'Network.MacAddress' :> Network {
                doc 
                /* Media Access Control Address. 
                 *
                 * The unique physical address of the network hardware.*/
                constant attribute subType :>> ActiveAxes::subType : Profile::DataTypes::DataItemSubTypeEnum :> ActiveAxes::subType default subType::MAC_ADDRESS;
            }
            part def 'Network.Wireless' :> Network {
                doc /* identifies whether the connection type is wireless.*/
                constant attribute subType :>> ActiveAxes::subType : Profile::DataTypes::DataItemSubTypeEnum :> ActiveAxes::subType default subType::WIRELESS;
                attribute result [0..1] :>> result : Profile::DataTypes::NetworkWirelessEnum :> result;
            }
            part def Rotation :> Event {
                doc /* {{def(EventEnum::ROTATION)}}*/
                constant attribute units :>> units : Profile::DataTypes::UnitEnum :> units default units::DEGREE_3D;
                constant attribute type :>> type : Profile::DataTypes::EventEnum :> type default type::ROTATION;
                attribute result [0..1] :>> result : Profile::DataTypes::float3d;
            }
            part def Translation :> Event {
                doc /* {{def(EventEnum::TRANSLATION)}}*/
                constant attribute units :>> units : Profile::DataTypes::UnitEnum :> units default units::MILLIMETER_3D;
                constant attribute type :>> type : Profile::DataTypes::EventEnum :> type default type::TRANSLATION;
                attribute result [0..1] :>> result : Profile::DataTypes::float3d;
            }
            part def ProcessKindId :> Event {
                doc /* {{def(EventEnum::PROCESS_KIND_ID)}}*/
                constant attribute type :>> type : Profile::DataTypes::EventEnum :> type default type::PROCESS_KIND_ID;
            }
            part def PartStatus :> Event {
                doc 
                /* {{def(EventEnum::PART_STATUS)}}
                 *
                 * If unique identifier is given, part status is for that individual. If group identifier is given without a unique identifier, then the status is assumed to be for the whole group.*/
                attribute result [0..1] :>> result : Profile::DataTypes::PartStatusEnum :> result;
                constant attribute type :>> type : Profile::DataTypes::EventEnum :> type default type::PART_STATUS;
            }
            part def AlarmLimit :> Event {
                doc /* {{def(EventEnum::ALARM_LIMIT)}}*/
                constant attribute type :>> type : Profile::DataTypes::EventEnum :> type default type::ALARM_LIMIT;
                part result [0..1] :>> result : Profile::DataTypes::AlarmLimitResult;
            }
            part def ProcessAggregateId :> Event {
                doc /* {{def(EventEnum::PROCESS_AGGREGATE_ID)}}*/
                constant attribute type :>> type : Profile::DataTypes::EventEnum :> type default type::PROCESS_AGGREGATE_ID;
            }
            part def 'ProcessKindId.Uuid' :> ProcessKindId {
                doc /* universally unique identifier as specified in ISO 11578 or RFC 4122.*/
                constant attribute subType :>> subType : Profile::DataTypes::DataItemSubTypeEnum :> subType default subType::UUID;
            }
            part def 'ProcessAggregateId.OrderNumber' :> ProcessAggregateId {
                doc /* identifier of the authorization of the process occurrence. Synonyms include "job id", "work order".*/
                constant attribute subType :>> subType : Profile::DataTypes::DataItemSubTypeEnum :> subType default subType::ORDER_NUMBER;
            }
            part def 'ProcessKindId.ISOStepExecutable' :> ProcessKindId {
                doc /* reference to a ISO 10303 Executable.*/
                constant attribute subType :>> subType : Profile::DataTypes::DataItemSubTypeEnum :> subType default subType::ISO_STEP_EXECUTABLE;
            }
            part def PartKindId :> Event {
                doc 
                /* {{def(EventEnum::PART_KIND_ID)}}
                 *
                 * If no {{property(DataItem::subType)}} is specified, `UUID` is default.*/
                constant attribute type :>> type : Profile::DataTypes::EventEnum :> type default type::PART_KIND_ID;
                constant attribute subType :>> subType : Profile::DataTypes::DataItemSubTypeEnum :> subType default subType::UUID;
            }
            part def 'ProcessKindId.ProcessName' :> ProcessKindId {
                doc /* word or set of words by which a process being executed (process occurrence) by the device is known, addressed, or referred to.*/
                constant attribute subType :>> subType : Profile::DataTypes::DataItemSubTypeEnum :> subType default subType::PROCESS_NAME;
            }
            part def AdapterURI :> Event {
                doc /* {{def(EventEnum::ADAPTER_URI)}}*/
                constant attribute type :>> type : Profile::DataTypes::EventEnum :> type default type::ADAPTER_URI;
            }
            part def 'PartKindId.Uuid' :> PartKindId {
                doc /* universally unique identifier as specified in ISO 11578 or RFC 4122.*/
                constant attribute subType :>> ActiveAxes::subType : Profile::DataTypes::DataItemSubTypeEnum :> ActiveAxes::subType default subType::UUID;
            }
            part def DeviceRemoved :> Event {
                doc /* {{def(EventEnum::DEVICE_REMOVED)}}*/
                constant attribute type :>> type : Profile::DataTypes::EventEnum :> type default type::DEVICE_REMOVED;
                attribute hash [0..1] : Profile::DataTypes::string {
                    doc /* condensed message digest from a secure one-way hash function. {{cite(FIPS PUB 180-4)}}*/
                }
            }
            part def DeviceChanged :> Event {
                doc /* {{def(EventEnum::DEVICE_CHANGED)}}*/
                constant attribute type :>> type : Profile::DataTypes::EventEnum :> type default type::DEVICE_CHANGED;
                attribute hash [0..1] : Profile::DataTypes::string {
                    doc /* condensed message digest from a secure one-way hash function. {{cite(FIPS PUB 180-4)}}*/
                }
            }
            part def SpecificationLimit :> Event {
                doc /* {{def(EventEnum::SPECIFICATION_LIMIT)}}*/
                constant attribute type :>> type : Profile::DataTypes::EventEnum :> type default type::SPECIFICATION_LIMIT;
                part result [0..1] :>> result : Profile::DataTypes::SpecificationLimitResult;
            }
            part def ConnectionStatus :> Event {
                doc /* {{def(EventEnum::CONNECTION_STATUS)}}*/
                attribute result [0..1] :>> result : Profile::DataTypes::ConnectionStatusEnum :> result;
                constant attribute type :>> type : Profile::DataTypes::EventEnum :> type default type::CONNECTION_STATUS;
            }
            part def 'PartKindId.PartFamily' :> PartKindId {
                doc /* identifier given to a group of parts having similarities in geometry, manufacturing process, and/or functions.*/
                constant attribute subType :>> ActiveAxes::subType : Profile::DataTypes::DataItemSubTypeEnum :> ActiveAxes::subType default subType::PART_FAMILY;
            }
            part def 'PartKindId.PartName' :> PartKindId {
                doc /* word or set of words by which a part is known, addressed, or referred to.*/
                constant attribute subType :>> ActiveAxes::subType : Profile::DataTypes::DataItemSubTypeEnum :> ActiveAxes::subType default subType::PART_NAME;
            }
            part def AdapterSoftwareVersion :> Event {
                doc /* {{def(EventEnum::ADAPTER_SOFTWARE_VERSION)}}*/
                constant attribute type :>> type : Profile::DataTypes::EventEnum :> type default type::ADAPTER_SOFTWARE_VERSION;
            }
            part def SensorAttachment :> Event {
                doc /* {{def(EventEnum::SENSOR_ATTACHMENT)}}*/
                constant attribute type :>> type : Profile::DataTypes::EventEnum :> type default type::SENSOR_ATTACHMENT;
                part result [0..1] :>> result : Profile::DataTypes::SensorAttachmentResult;
            }
            part def 'PartKindId.PartNumber' :> PartKindId {
                doc /* identifier of a particular part design or model.*/
                constant attribute subType :>> ActiveAxes::subType : Profile::DataTypes::DataItemSubTypeEnum :> ActiveAxes::subType default subType::PART_NUMBER;
            }
            part def 'PartGroupId.Lot' :> PartGroupId {
                doc /* identifier that references a group of parts tracked as a lot.*/
                constant attribute subType :>> ActiveAxes::subType : Profile::DataTypes::DataItemSubTypeEnum :> ActiveAxes::subType default subType::LOT;
            }
            part def 'PartGroupId.RawMaterial' :> PartGroupId {
                doc /* material that is used to produce parts.*/
                constant attribute subType :>> ActiveAxes::subType : Profile::DataTypes::DataItemSubTypeEnum :> ActiveAxes::subType default subType::RAW_MATERIAL;
            }
            part def 'PartGroupId.Batch' :> PartGroupId {
                doc /* identifier that references a group of parts produced in a batch.*/
                constant attribute subType :>> ActiveAxes::subType : Profile::DataTypes::DataItemSubTypeEnum :> ActiveAxes::subType default subType::BATCH;
            }
            part def ControlLimit :> Event {
                doc /* {{def(EventEnum::CONTROL_LIMIT)}}*/
                constant attribute type :>> type : Profile::DataTypes::EventEnum :> type default type::CONTROL_LIMIT;
                part result [0..1] :>> result : Profile::DataTypes::ControlLimitResult;
            }
            part def DeviceAdded :> Event {
                doc /* {{def(EventEnum::DEVICE_ADDED)}}*/
                constant attribute type :>> type : Profile::DataTypes::EventEnum :> type default type::DEVICE_ADDED;
                attribute hash [0..1] : Profile::DataTypes::string {
                    doc /* condensed message digest from a secure one-way hash function. {{cite(FIPS PUB 180-4)}}*/
                }
            }
            part def 'ProcessAggregateId.ProcessStep' :> ProcessAggregateId {
                doc /* identifier of the step in the process plan that this occurrence corresponds to. Synonyms include "operation id".*/
                constant attribute subType :>> subType : Profile::DataTypes::DataItemSubTypeEnum :> subType default subType::PROCESS_STEP;
            }
            part def MTConnectVersion :> Event {
                doc /* {{def(EventEnum::MTCONNECT_VERSION)}}*/
                constant attribute type :>> type : Profile::DataTypes::EventEnum :> type default type::MTCONNECT_VERSION;
            }
            part def 'PartUniqueId.SerialNumber' :> PartUniqueId {
                doc /* serial number that uniquely identifies a specific part.*/
                constant attribute subType :>> ActiveAxes::subType : Profile::DataTypes::DataItemSubTypeEnum :> ActiveAxes::subType default subType::SERIAL_NUMBER;
            }
            part def 'PartUniqueId.RawMaterial' :> PartUniqueId {
                doc /* material that is used to produce parts.*/
                constant attribute subType :>> ActiveAxes::subType : Profile::DataTypes::DataItemSubTypeEnum :> ActiveAxes::subType default subType::RAW_MATERIAL;
            }
            part def 'PartGroupId.Uuid' :> PartGroupId {
                doc /* universally unique identifier as specified in ISO 11578 or RFC 4122.*/
                constant attribute subType :>> ActiveAxes::subType : Profile::DataTypes::DataItemSubTypeEnum :> ActiveAxes::subType default subType::UUID;
            }
            part def ProcessOccurrenceId :> Event {
                doc /* {{def(EventEnum::PROCESS_OCCURRENCE_ID)}}*/
                constant attribute type :>> type : Profile::DataTypes::EventEnum :> type default type::PROCESS_OCCURRENCE_ID;
            }
            part def 'ProcessAggregateId.ProcessPlan' :> ProcessAggregateId {
                doc /* identifier of the process plan that this occurrence belongs to. Synonyms include "routing id", "job id".*/
                constant attribute subType :>> subType : Profile::DataTypes::DataItemSubTypeEnum :> subType default subType::PROCESS_PLAN;
            }
            part def 'PartUniqueId.Uuid' :> PartUniqueId {
                doc /* universally unique identifier as specified in ISO 11578 or RFC 4122.*/
                constant attribute subType :>> ActiveAxes::subType : Profile::DataTypes::DataItemSubTypeEnum :> ActiveAxes::subType default subType::UUID;
            }
            part def PartGroupId :> Event {
                doc 
                /* {{def(EventEnum::PART_GROUP_ID)}}
                 *
                 * If no {{property(DataItem::subType)}} is specified, `UUID` is default.*/
                constant attribute type :>> type : Profile::DataTypes::EventEnum :> type default type::PART_GROUP_ID;
                constant attribute subType :>> subType : Profile::DataTypes::DataItemSubTypeEnum :> subType default subType::UUID;
            }
            part def 'PartGroupId.HeatTreat' :> PartGroupId {
                doc /* identifier used to reference a material heat number.*/
                constant attribute subType :>> ActiveAxes::subType : Profile::DataTypes::DataItemSubTypeEnum :> ActiveAxes::subType default subType::HEAT_TREAT;
            }
            part def PartUniqueId :> Event {
                doc 
                /* {{def(EventEnum::PART_UNIQUE_ID)}}
                 *
                 * If no {{property(DataItem::subType)}} is specified, `UUID` is default.*/
                constant attribute type :>> type : Profile::DataTypes::EventEnum :> type default type::PART_UNIQUE_ID;
                constant attribute subType :>> subType : Profile::DataTypes::DataItemSubTypeEnum :> subType default subType::UUID;
            }
            part def 'LoadCount.Remaining' :> LoadCount {
                doc /* accumulation of actions, items, or activities yet to be counted.*/
                constant attribute subType [1] :>> ActiveAxes::subType : Profile::DataTypes::DataItemSubTypeEnum :> ActiveAxes::subType default subType::REMAINING;
            }
            part def 'ActivationCount.Target' :> ActivationCount {
                doc /* goal of the operation or process.*/
                constant attribute subType [1] :>> ActiveAxes::subType : Profile::DataTypes::DataItemSubTypeEnum :> ActiveAxes::subType default subType::TARGET;
            }
            part def 'ActivationCount.Good' :> ActivationCount {
                doc /* accumulation of actions, items, or activities being counted that conform to specification or expectation.*/
                constant attribute subType [1] :>> ActiveAxes::subType : Profile::DataTypes::DataItemSubTypeEnum :> ActiveAxes::subType default subType::GOOD;
            }
            part def 'TransferCount.Good' :> TransferCount {
                doc /* accumulation of actions, items, or activities being counted that conform to specification or expectation.*/
                constant attribute subType [1] :>> ActiveAxes::subType : Profile::DataTypes::DataItemSubTypeEnum :> ActiveAxes::subType default subType::GOOD;
            }
            part def 'CycleCount.Good' :> CycleCount {
                doc /* accumulation of actions, items, or activities being counted that conform to specification or expectation.*/
                constant attribute subType [1] :>> ActiveAxes::subType : Profile::DataTypes::DataItemSubTypeEnum :> ActiveAxes::subType default subType::GOOD;
            }
            part def ActivationCount :> Event {
                doc /* {{def(EventEnum::ACTIVATION_COUNT)}}*/
                constant attribute type :>> type : Profile::DataTypes::EventEnum :> type default type::ACTIVATION_COUNT;
                constant attribute subType :>> subType : Profile::DataTypes::DataItemSubTypeEnum :> subType default subType::ALL;
                attribute result [0..1] :>> result : Profile::DataTypes::integer;
            }
            part def 'UnloadCount.Aborted' :> UnloadCount {
                doc /* accumulation of actions or activities that were attempted, but terminated before they could be completed.*/
                constant attribute subType [1] :>> ActiveAxes::subType : Profile::DataTypes::DataItemSubTypeEnum :> ActiveAxes::subType default subType::ABORTED;
            }
            part def 'CycleCount.Remaining' :> CycleCount {
                doc /* accumulation of actions, items, or activities yet to be counted.*/
                constant attribute subType [1] :>> ActiveAxes::subType : Profile::DataTypes::DataItemSubTypeEnum :> ActiveAxes::subType default subType::REMAINING;
            }
            part def 'DeactivationCount.Bad' :> DeactivationCount {
                doc /* accumulation of actions, items, or activities being counted that do not conform to specification or expectation.*/
                constant attribute subType [1] :>> ActiveAxes::subType : Profile::DataTypes::DataItemSubTypeEnum :> ActiveAxes::subType default subType::BAD;
            }
            part def 'TransferCount.Aborted' :> TransferCount {
                doc /* accumulation of actions or activities that were attempted, but terminated before they could be completed.*/
                constant attribute subType [1] :>> ActiveAxes::subType : Profile::DataTypes::DataItemSubTypeEnum :> ActiveAxes::subType default subType::ABORTED;
            }
            part def DeactivationCount :> Event {
                doc /* {{def(EventEnum::DEACTIVATION_COUNT)}}*/
                constant attribute subType :>> subType : Profile::DataTypes::DataItemSubTypeEnum :> subType default subType::ALL;
                constant attribute type :>> type : Profile::DataTypes::EventEnum :> type default type::DEACTIVATION_COUNT;
                attribute result [0..1] :>> result : Profile::DataTypes::integer;
            }
            part def 'ActivationCount.Bad' :> ActivationCount {
                doc /* accumulation of actions, items, or activities being counted that do not conform to specification or expectation.*/
                constant attribute subType [1] :>> ActiveAxes::subType : Profile::DataTypes::DataItemSubTypeEnum :> ActiveAxes::subType default subType::BAD;
            }
            part def 'UnloadCount.Bad' :> UnloadCount {
                doc /* accumulation of actions, items, or activities being counted that do not conform to specification or expectation.*/
                constant attribute subType [1] :>> ActiveAxes::subType : Profile::DataTypes::DataItemSubTypeEnum :> ActiveAxes::subType default subType::BAD;
            }
            part def 'CycleCount.Complete' :> CycleCount {
                doc /* accumulation of actions, items, or activities that have been completed, independent of the outcome.*/
                constant attribute subType [1] :>> ActiveAxes::subType : Profile::DataTypes::DataItemSubTypeEnum :> ActiveAxes::subType default subType::COMPLETE;
            }
            part def TransferCount :> Event {
                doc /* {{def(EventEnum::TRANSFER_COUNT)}}*/
                constant attribute subType :>> subType : Profile::DataTypes::DataItemSubTypeEnum :> subType default subType::ALL;
                constant attribute type :>> type : Profile::DataTypes::EventEnum :> type default type::TRANSFER_COUNT;
                attribute result [0..1] :>> result : Profile::DataTypes::integer;
            }
            part def 'LoadCount.Bad' :> LoadCount {
                doc /* accumulation of actions, items, or activities being counted that do not conform to specification or expectation.*/
                constant attribute subType [1] :>> ActiveAxes::subType : Profile::DataTypes::DataItemSubTypeEnum :> ActiveAxes::subType default subType::BAD;
            }
            part def 'CycleCount.Aborted' :> CycleCount {
                doc /* accumulation of actions or activities that were attempted, but terminated before they could be completed.*/
                constant attribute subType [1] :>> ActiveAxes::subType : Profile::DataTypes::DataItemSubTypeEnum :> ActiveAxes::subType default subType::ABORTED;
            }
            part def LoadCount :> Event {
                doc /* {{def(EventEnum::LOAD_COUNT)}}*/
                constant attribute subType :>> subType : Profile::DataTypes::DataItemSubTypeEnum :> subType default subType::ALL;
                constant attribute type :>> type : Profile::DataTypes::EventEnum :> type default type::LOAD_COUNT;
                attribute result [0..1] :>> result : Profile::DataTypes::integer;
            }
            part def 'TransferCount.Failed' :> TransferCount {
                doc /* accumulation of actions, items, or activities being counted that do not conform to specification or expectation.*/
                constant attribute subType [1] :>> ActiveAxes::subType : Profile::DataTypes::DataItemSubTypeEnum :> ActiveAxes::subType default subType::FAILED;
            }
            part def 'DeactivationCount.Failed' :> DeactivationCount {
                doc /* accumulation of actions or activities that were attempted, but failed to complete or resulted in an unexpected or unacceptable outcome.*/
                constant attribute subType [1] :>> ActiveAxes::subType : Profile::DataTypes::DataItemSubTypeEnum :> ActiveAxes::subType default subType::FAILED;
            }
            part def 'LoadCount.Failed' :> LoadCount {
                doc /* accumulation of actions or activities that were attempted, but failed to complete or resulted in an unexpected or unacceptable outcome.*/
                constant attribute subType [1] :>> ActiveAxes::subType : Profile::DataTypes::DataItemSubTypeEnum :> ActiveAxes::subType default subType::FAILED;
            }
            part def PartProcessingState :> Event {
                doc /* {{def(EventEnum::PART_PROCESSING_STATE)}}*/
                attribute result [0..1] :>> result : Profile::DataTypes::PartProcessingStateEnum;
                constant attribute type :>> type : Profile::DataTypes::EventEnum :> type default type::PART_PROCESSING_STATE;
            }
            part def 'ActivationCount.Remaining' :> ActivationCount {
                doc /* accumulation of actions, items, or activities yet to be counted.*/
                constant attribute subType [1] :>> ActiveAxes::subType : Profile::DataTypes::DataItemSubTypeEnum :> ActiveAxes::subType default subType::REMAINING;
            }
            part def 'TransferCount.All' :> TransferCount {
                doc /* accumulation of all actions, items, or activities being counted independent of the outcome.*/
                constant attribute subType [1] :>> ActiveAxes::subType : Profile::DataTypes::DataItemSubTypeEnum :> ActiveAxes::subType default subType::ALL;
            }
            part def 'UnloadCount.Failed' :> UnloadCount {
                doc /* accumulation of actions, items, or activities being counted that do not conform to specification or expectation.*/
                constant attribute subType [1] :>> ActiveAxes::subType : Profile::DataTypes::DataItemSubTypeEnum :> ActiveAxes::subType default subType::FAILED;
            }
            part def ProcessState :> Event {
                doc /* {{def(EventEnum::PROCESS_STATE)}}*/
                attribute result [0..1] :>> result : Profile::DataTypes::ProcessStateEnum;
                constant attribute type :>> type : Profile::DataTypes::EventEnum :> type default type::PROCESS_STATE;
            }
            part def 'ActivationCount.Aborted' :> ActivationCount {
                doc /* accumulation of actions or activities that were attempted, but terminated before they could be completed.*/
                constant attribute subType [1] :>> ActiveAxes::subType : Profile::DataTypes::DataItemSubTypeEnum :> ActiveAxes::subType default subType::ABORTED;
            }
            part def 'PartCount.Complete' :> PartCount {
                doc /* accumulation of actions, items, or activities that have been completed, independent of the outcome.*/
                constant attribute subType [1] :>> ActiveAxes::subType : Profile::DataTypes::DataItemSubTypeEnum :> ActiveAxes::subType default subType::COMPLETE;
            }
            part def 'DeactivationCount.Target' :> DeactivationCount {
                doc /* goal of the operation or process.*/
                constant attribute subType [1] :>> ActiveAxes::subType : Profile::DataTypes::DataItemSubTypeEnum :> ActiveAxes::subType default subType::TARGET;
            }
            part def 'TransferCount.Bad' :> TransferCount {
                doc /* accumulation of actions, items, or activities being counted that do not conform to specification or expectation.*/
                constant attribute subType [1] :>> ActiveAxes::subType : Profile::DataTypes::DataItemSubTypeEnum :> ActiveAxes::subType default subType::BAD;
            }
            part def 'ActivationCount.Failed' :> ActivationCount {
                doc /* accumulation of actions or activities that were attempted, but failed to complete or resulted in an unexpected or unacceptable outcome.*/
                constant attribute subType [1] :>> ActiveAxes::subType : Profile::DataTypes::DataItemSubTypeEnum :> ActiveAxes::subType default subType::FAILED;
            }
            part def 'TransferCount.Remaining' :> TransferCount {
                doc /* accumulation of actions, items, or activities yet to be counted.*/
                constant attribute subType [1] :>> ActiveAxes::subType : Profile::DataTypes::DataItemSubTypeEnum :> ActiveAxes::subType default subType::REMAINING;
            }
            part def 'DeactivationCount.Complete' :> DeactivationCount {
                doc /* accumulation of actions, items, or activities that have been completed, independent of the outcome.*/
                constant attribute subType [1] :>> ActiveAxes::subType : Profile::DataTypes::DataItemSubTypeEnum :> ActiveAxes::subType default subType::COMPLETE;
            }
            part def 'LoadCount.Aborted' :> LoadCount {
                doc /* accumulation of actions or activities that were attempted, but terminated before they could be completed.*/
                constant attribute subType [1] :>> ActiveAxes::subType : Profile::DataTypes::DataItemSubTypeEnum :> ActiveAxes::subType default subType::ABORTED;
            }
            part def 'UnloadCount.Good' :> UnloadCount {
                doc /* accumulation of actions, items, or activities being counted that conform to specification or expectation.*/
                constant attribute subType [1] :>> ActiveAxes::subType : Profile::DataTypes::DataItemSubTypeEnum :> ActiveAxes::subType default subType::GOOD;
            }
            part def 'DeactivationCount.Remaining' :> DeactivationCount {
                doc /* accumulation of actions, items, or activities yet to be counted.*/
                constant attribute subType [1] :>> ActiveAxes::subType : Profile::DataTypes::DataItemSubTypeEnum :> ActiveAxes::subType default subType::REMAINING;
            }
            part def 'CycleCount.Bad' :> CycleCount {
                doc /* accumulation of actions, items, or activities being counted that do not conform to specification or expectation.*/
                constant attribute subType [1] :>> ActiveAxes::subType : Profile::DataTypes::DataItemSubTypeEnum :> ActiveAxes::subType default subType::BAD;
            }
            part def 'TransferCount.Complete' :> TransferCount {
                doc /* accumulation of actions, items, or activities that have been completed, independent of the outcome.*/
                constant attribute subType [1] :>> ActiveAxes::subType : Profile::DataTypes::DataItemSubTypeEnum :> ActiveAxes::subType default subType::COMPLETE;
            }
            part def 'UnloadCount.Complete' :> UnloadCount {
                doc /* accumulation of actions, items, or activities that have been completed, independent of the outcome.*/
                constant attribute subType [1] :>> ActiveAxes::subType : Profile::DataTypes::DataItemSubTypeEnum :> ActiveAxes::subType default subType::COMPLETE;
            }
            part def 'UnloadCount.All' :> UnloadCount {
                doc /* accumulation of all actions, items, or activities being counted independent of the outcome.*/
                constant attribute subType [1] :>> ActiveAxes::subType : Profile::DataTypes::DataItemSubTypeEnum :> ActiveAxes::subType default subType::ALL;
            }
            part def ValveState :> Event {
                doc /* {{def(EventEnum::VALVE_STATE)}}*/
                attribute result [0..1] :>> result : Profile::DataTypes::ValveStateEnum;
                constant attribute type :>> type : Profile::DataTypes::EventEnum :> type default type::VALVE_STATE;
            }
            part def 'CycleCount.Failed' :> CycleCount {
                doc /* accumulation of actions or activities that were attempted, but failed to complete or resulted in an unexpected or unacceptable outcome.*/
                constant attribute subType [1] :>> ActiveAxes::subType : Profile::DataTypes::DataItemSubTypeEnum :> ActiveAxes::subType default subType::FAILED;
            }
            part def 'LoadCount.All' :> LoadCount {
                doc /* accumulation of all actions, items, or activities being counted independent of the outcome.*/
                constant attribute subType [1] :>> ActiveAxes::subType : Profile::DataTypes::DataItemSubTypeEnum :> ActiveAxes::subType default subType::ALL;
            }
            part def 'UnloadCount.Target' :> UnloadCount {
                doc /* goal of the operation or process.*/
                constant attribute subType [1] :>> ActiveAxes::subType : Profile::DataTypes::DataItemSubTypeEnum :> ActiveAxes::subType default subType::TARGET;
            }
            part def 'ValveState.Actual' :> ValveState {
                doc /* measured or reported value of an {{term(observation)}}.*/
                constant attribute subType :>> subType : Profile::DataTypes::DataItemSubTypeEnum :> subType default subType::ACTUAL;
            }
            part def 'TransferCount.Target' :> TransferCount {
                doc /* goal of the operation or process.*/
                constant attribute subType [1] :>> ActiveAxes::subType : Profile::DataTypes::DataItemSubTypeEnum :> ActiveAxes::subType default subType::TARGET;
            }
            part def 'CycleCount.Target' :> CycleCount {
                doc /* goal of the operation or process.*/
                constant attribute subType [1] :>> ActiveAxes::subType : Profile::DataTypes::DataItemSubTypeEnum :> ActiveAxes::subType default subType::TARGET;
            }
            part def LockState :> Event {
                doc /* {{def(EventEnum::LOCK_STATE)}}*/
                attribute result [0..1] :>> result : Profile::DataTypes::LockStateEnum;
                constant attribute type :>> type : Profile::DataTypes::EventEnum :> type default type::LOCK_STATE;
            }
            part def UnloadCount :> Event {
                doc /* {{def(EventEnum::UNLOAD_COUNT)}}*/
                constant attribute subType :>> subType : Profile::DataTypes::DataItemSubTypeEnum :> subType default subType::ALL;
                constant attribute type :>> type : Profile::DataTypes::EventEnum :> type default type::UNLOAD_COUNT;
                attribute result [0..1] :>> result : Profile::DataTypes::integer;
            }
            part def 'PartCount.Aborted' :> PartCount {
                doc /* accumulation of actions or activities that were attempted, but terminated before they could be completed.*/
                constant attribute subType [1] :>> ActiveAxes::subType : Profile::DataTypes::DataItemSubTypeEnum :> ActiveAxes::subType default subType::ABORTED;
            }
            part def 'ActivationCount.Complete' :> ActivationCount {
                doc /* accumulation of actions, items, or activities that have been completed, independent of the outcome.*/
                constant attribute subType [1] :>> ActiveAxes::subType : Profile::DataTypes::DataItemSubTypeEnum :> ActiveAxes::subType default subType::COMPLETE;
            }
            part def 'PartCount.Failed' :> PartCount {
                doc /* accumulation of actions or activities that were attempted, but failed to complete or resulted in an unexpected or unacceptable outcome.*/
                constant attribute subType [1] :>> ActiveAxes::subType : Profile::DataTypes::DataItemSubTypeEnum :> ActiveAxes::subType default subType::FAILED;
            }
            part def 'LoadCount.Good' :> LoadCount {
                doc /* accumulation of actions, items, or activities being counted that conform to specification or expectation.*/
                constant attribute subType [1] :>> ActiveAxes::subType : Profile::DataTypes::DataItemSubTypeEnum :> ActiveAxes::subType default subType::GOOD;
            }
            part def CycleCount :> Event {
                doc /* {{def(EventEnum::CYCLE_COUNT)}}*/
                constant attribute subType :>> subType : Profile::DataTypes::DataItemSubTypeEnum :> subType default subType::ALL;
                constant attribute type :>> type : Profile::DataTypes::EventEnum :> type default type::CYCLE_COUNT;
                attribute result [0..1] :>> result : Profile::DataTypes::integer;
            }
            part def 'CycleCount.All' :> CycleCount {
                doc /* accumulation of all actions, items, or activities being counted independent of the outcome.*/
                constant attribute subType [1] :>> ActiveAxes::subType : Profile::DataTypes::DataItemSubTypeEnum :> ActiveAxes::subType default subType::ALL;
            }
            part def 'LoadCount.Complete' :> LoadCount {
                doc /* accumulation of actions, items, or activities that have been completed, independent of the outcome.*/
                constant attribute subType [1] :>> ActiveAxes::subType : Profile::DataTypes::DataItemSubTypeEnum :> ActiveAxes::subType default subType::COMPLETE;
            }
            part def 'ActivationCount.All' :> ActivationCount {
                doc /* accumulation of all actions, items, or activities being counted independent of the outcome.*/
                constant attribute subType [1] :>> ActiveAxes::subType : Profile::DataTypes::DataItemSubTypeEnum :> ActiveAxes::subType default subType::ALL;
            }
            part def 'DeactivationCount.All' :> DeactivationCount {
                doc /* accumulation of all actions, items, or activities being counted independent of the outcome.*/
                constant attribute subType [1] :>> ActiveAxes::subType : Profile::DataTypes::DataItemSubTypeEnum :> ActiveAxes::subType default subType::ALL;
            }
            part def 'UnloadCount.Remaining' :> UnloadCount {
                doc /* accumulation of actions, items, or activities yet to be counted.*/
                constant attribute subType [1] :>> ActiveAxes::subType : Profile::DataTypes::DataItemSubTypeEnum :> ActiveAxes::subType default subType::REMAINING;
            }
            part def 'DeactivationCount.Good' :> DeactivationCount {
                doc /* accumulation of actions, items, or activities being counted that conform to specification or expectation.*/
                constant attribute subType [1] :>> ActiveAxes::subType : Profile::DataTypes::DataItemSubTypeEnum :> ActiveAxes::subType default subType::GOOD;
            }
            part def 'LoadCount.Target' :> LoadCount {
                doc /* goal of the operation or process.*/
                constant attribute subType [1] :>> ActiveAxes::subType : Profile::DataTypes::DataItemSubTypeEnum :> ActiveAxes::subType default subType::TARGET;
            }
            part def 'ValveState.Programmed' :> ValveState {
                doc 
                /* directive value without offsets and adjustments.
                 *
                 */
                constant attribute subType :>> subType : Profile::DataTypes::DataItemSubTypeEnum :> subType default subType::PROGRAMMED;
            }
            part def 'DeactivationCount.Aborted' :> DeactivationCount {
                doc /* accumulation of actions or activities that were attempted, but terminated before they could be completed.*/
                constant attribute subType [1] :>> ActiveAxes::subType : Profile::DataTypes::DataItemSubTypeEnum :> ActiveAxes::subType default subType::ABORTED;
            }
            part def OperatingMode :> Event {
                doc /* {{def(EventEnum::OPERATING_MODE)}}*/
                attribute result [0..1] :>> result : Profile::DataTypes::OperatingModeEnum :> result;
                constant attribute type :>> type : Profile::DataTypes::EventEnum :> type default type::OPERATING_MODE;
            }
            part def AssetCount :> Event {
                doc /* {{def(EventEnum::ASSET_COUNT)}}*/
                constant attribute type :>> type : Profile::DataTypes::EventEnum :> type default type::ASSET_COUNT;
                attribute result [0..1] :>> result : Profile::DataTypes::integer;
            }
            part def MaintenanceList :> Event {
                doc 
                /* {{def(EventEnum::MAINTENANCE_LIST)}}
                 *
                 * If {{property(MaintenanceList::result::Interval)}} `key` is not provided, it is assumed `ABSOLUTE`.
                 *
                 * If {{property(MaintenanceList::result::Direction)}} `key` is not provided, it is assumed `UP`.
                 *
                 * If {{property(MaintenanceList::result::Units)}} `key` is not provided, it is assumed to be `COUNT`.*/
                constant attribute type :>> type : Profile::DataTypes::EventEnum :> type default type::MAINTENANCE_LIST;
                part result [0..1] :>> result : Profile::DataTypes::MaintenanceListResult;
            }
            part def FixtureId :> Event {
                doc /* {{def(EventEnum::FIXTURE_ID)}}*/
                constant attribute type :>> type : Profile::DataTypes::EventEnum :> type default type::FIXTURE_ID;
            }
            part def PartCountType :> Event {
                doc /* {{def(EventEnum::PART_COUNT_TYPE)}}*/
                attribute result [0..1] :>> result : Profile::DataTypes::PartCountTypeEnum :> result;
                constant attribute type :>> type : Profile::DataTypes::EventEnum :> type default type::PART_COUNT_TYPE;
            }
            part def 'Program.Activity' :> Program {
                doc /* phase or segment of a recipe or program.*/
                constant attribute subType :>> subType : Profile::DataTypes::DataItemSubTypeEnum :> subType default subType::ACTIVITY;
            }
            part def 'Program.Segment' :> Program {
                doc /* phase of a recipe process.*/
                constant attribute subType :>> subType : Profile::DataTypes::DataItemSubTypeEnum :> subType default subType::SEGMENT;
            }
            part def 'Program.Recipe' :> Program {
                doc /* process as part of product production; can be a subprocess of a larger process.*/
                constant attribute subType :>> subType : Profile::DataTypes::DataItemSubTypeEnum :> subType default subType::RECIPE;
            }
            part def 'Program.Operation' :> Program {
                doc /* step of a discrete manufacturing process.*/
                constant attribute subType :>> subType : Profile::DataTypes::DataItemSubTypeEnum :> subType default subType::OPERATION;
            }
            part def 'ProcessOccurrenceId.Activity' :> ProcessOccurrenceId {
                doc /* phase or segment of a recipe or program.*/
                constant attribute subType :>> subType : Profile::DataTypes::DataItemSubTypeEnum :> subType default subType::ACTIVITY;
            }
            part def 'ProcessOccurrenceId.Segment' :> ProcessOccurrenceId {
                doc /* phase of a recipe process.*/
                constant attribute subType :>> subType : Profile::DataTypes::DataItemSubTypeEnum :> subType default subType::SEGMENT;
            }
            part def 'ProcessOccurrenceId.Recipe' :> ProcessOccurrenceId {
                doc /* process as part of product production; can be a subprocess of a larger process.*/
                constant attribute subType :>> subType : Profile::DataTypes::DataItemSubTypeEnum :> subType default subType::RECIPE;
            }
            part def 'ProcessOccurrenceId.Operation' :> ProcessOccurrenceId {
                doc /* step of a discrete manufacturing process.*/
                constant attribute subType :>> subType : Profile::DataTypes::DataItemSubTypeEnum :> subType default subType::OPERATION;
            }
            part def 'Program.Active' :> Program {
                doc /* identity of the logic or motion program currently executing.*/
                constant attribute subType :>> subType : Profile::DataTypes::DataItemSubTypeEnum :> subType default subType::ACTIVE;
            }
            part def 'Program.Main' :> Program {
                doc 
                /* identity of the primary logic or motion program currently being executed. 
                 *
                 * It is the starting nest level in a call structure and may contain calls to sub programs.*/
                constant attribute subType :>> subType : Profile::DataTypes::DataItemSubTypeEnum :> subType default subType::MAIN;
            }
            part def 'Program.Schedule' :> Program {
                doc /* identity of a control program that is used to specify the order of execution of other programs.*/
                constant attribute subType :>> subType : Profile::DataTypes::DataItemSubTypeEnum :> subType default subType::SCHEDULE;
            }
            part def ClockTime :> Event {
                doc /* {{def(EventEnum::CLOCK_TIME)}}*/
                constant attribute type :>> Sample::type : Profile::DataTypes::EventEnum :> ActiveAxes::type default type::CLOCK_TIME;
                attribute result [0..1] :>> result : Profile::DataTypes::datetime :> result;
            }
            part def 'ProgramComment.Main' :> ProgramComment {
                doc 
                /* identity of the primary logic or motion program currently being executed. 
                 *
                 * It is the starting nest level in a call structure and may contain calls to sub programs.*/
                constant attribute subType :>> subType : Profile::DataTypes::DataItemSubTypeEnum :> subType default subType::MAIN;
            }
            part def 'ProgramComment.Schedule' :> ProgramComment {
                doc /* identity of a control program that is used to specify the order of execution of other programs.*/
                constant attribute subType :>> subType : Profile::DataTypes::DataItemSubTypeEnum :> subType default subType::SCHEDULE;
            }
            part def 'ProgramComment.Active' :> ProgramComment {
                doc /* identity of the logic or motion program currently executing.*/
                constant attribute subType :>> subType : Profile::DataTypes::DataItemSubTypeEnum :> subType default subType::ACTIVE;
            }
            part def NetworkPort :> Event {
                doc /* {{def(EventEnum::NETWORK_PORT)}}*/
                constant attribute type :>> type : Profile::DataTypes::EventEnum :> type default type::NETWORK_PORT;
                attribute result [0..1] :>> result : Profile::DataTypes::integer;
            }
            part def HostName :> Event {
                doc /* {{def(EventEnum::HOST_NAME)}}*/
                constant attribute type :>> type : Profile::DataTypes::EventEnum :> type default type::HOST_NAME;
            }
            part def LeakDetect :> Event {
                doc /* {{def(EventEnum::LEAK_DETECT)}}*/
                attribute result [0..1] :>> result : Profile::DataTypes::LeakDetectEnum :> result;
                constant attribute type :>> type : Profile::DataTypes::EventEnum :> type default type::LEAK_DETECT;
            }
            part def BatteryState :> Event {
                doc /* {{def(EventEnum::BATTERY_STATE)}}*/
                attribute result [0..1] :>> result : Profile::DataTypes::BatteryStateEnum :> result;
                constant attribute type :>> type : Profile::DataTypes::EventEnum :> type default type::BATTERY_STATE;
            }
            part def FeaturePersisitentId :> Event {
                doc /* {{def(EventEnum::FEATURE_PERSISTENT_ID)}}*/
                constant attribute type :>> type : Profile::DataTypes::EventEnum :> type default type::FEATURE_PERSISTENT_ID;
                attribute result [0..1] :>> result : Profile::DataTypes::ID;
            }
            part def SensorState :> Event {
                doc /* {{def(EventEnum::SENSOR_STATE)}}*/
                constant attribute type :>> type : Profile::DataTypes::EventEnum :> type default type::SENSOR_STATE;
                constant attribute subType [1] :>> subType : Profile::DataTypes::DataItemSubTypeEnum :> subType default subType::BINARY;
            }
            part def 'SensorState.Binary' :> SensorState {
                doc /* {{def(EventEnum::SENSOR_STATE)}} where the state is {{def(DataItemSubTypeEnum::BINARY)}}*/
                constant attribute subType :>> ActiveAxes::subType : Profile::DataTypes::DataItemSubTypeEnum :> ActiveAxes::subType default subType::BINARY;
                attribute result [0..1] :>> result : Profile::DataTypes::binary;
            }
            part def 'SensorState.Boolean' :> SensorState {
                doc /* {{def(EventEnum::SENSOR_STATE)}} where the state is {{def(DataItemSubTypeEnum::BOOLEAN)}}*/
                constant attribute subType :>> ActiveAxes::subType : Profile::DataTypes::DataItemSubTypeEnum :> ActiveAxes::subType default subType::BOOLEAN;
                attribute result [0..1] :>> result : Profile::DataTypes::boolean;
            }
            part def 'SensorState.Enumerated' :> SensorState {
                doc /* {{def(EventEnum::SENSOR_STATE)}} where the state is {{def(DataItemSubTypeEnum::ENUMERATED)}}*/
                constant attribute subType :>> ActiveAxes::subType : Profile::DataTypes::DataItemSubTypeEnum :> ActiveAxes::subType default subType::ENUMERATED;
                attribute result [0..1] :>> result : Profile::DataTypes::integer;
            }
            part def 'SensorState.Detect' :> SensorState {
                doc /* {{def(EventEnum::SENSOR_STATE)}} where the state is {{def(DataItemSubTypeEnum::DETECT)}}*/
                constant attribute subType :>> ActiveAxes::subType : Profile::DataTypes::SensorStateDetectEnum :> ActiveAxes::subType default subType::DETECT;
                attribute result [0..1] :>> result : Profile::DataTypes::CompositionStateSwitchedEnum;
            }
            part def ComponentData :> Event {
                doc 
                /* tabular {{def(EventEnum::COMPONENT_DATA)}}
                 *
                 * If the {{block(Component)}} multiplicity can be determined, the device model **MUST** use a fixed set of {{block(Component)}}s.
                 *
                 * {{block(ComponentData)}} **MUST** provide a {{block(DataItem)}} {{block(Definition)}}.*/
                constant attribute type :>> type : Profile::DataTypes::EventEnum :> type default type::COMPONENT_DATA;
            }
            part def WorkOffsets :> Event {
                doc /* tabular representation of {{def(EventEnum::WORK_OFFSETS)}}*/
                constant attribute type :>> type : Profile::DataTypes::EventEnum :> type default type::WORK_OFFSETS;
            }
            part def ToolOffsets :> Event {
                doc /* tabular representation of {{def(EventEnum::TOOL_OFFSETS)}}*/
                constant attribute type :>> type : Profile::DataTypes::EventEnum :> type default type::TOOL_OFFSETS;
            }
            part def FeatureMeasurement :> Event {
                doc 
                /* tabular representation of {{def(EventEnum::FEATURE_MEASUREMENT)}}
                 *
                 * {{block(FeatureMeasurement)}} **MAY** include a {{term(characteristic)}} in which case it **MAY** include a `CHARACTERISTIC_STATUS`.*/
                constant attribute type :>> type : Profile::DataTypes::EventEnum :> type default type::FEATURE_MEASUREMENT;
                part result [0..1] :>> result : Profile::DataTypes::FeatureMeasurementResult;
            }
            part def CharacteristicPersistentId :> Event {
                doc /* {{def(EventEnum::CHARACTERISTIC_PERSISTENT_ID)}}*/
                constant attribute type :>> type : Profile::DataTypes::EventEnum :> type default type::ADAPTER_URI;
                attribute result [0..1] :>> result : Profile::DataTypes::ID;
            }
            part def MeasurementType :> Event {
                doc 
                /* {{def(EventEnum::MEASUREMENT_TYPE)}}
                 *
                 * Examples: `POINT`, `RADIUS`, `ANGLE`, `LENGTH`, etc.*/
                constant attribute type :>> type : Profile::DataTypes::EventEnum :> type default type::MEASUREMENT_TYPE;
            }
            part def MeasurementValue :> Event {
                doc /* {{def(EventEnum::MEASUREMENT_VALUE)}}*/
                constant attribute type :>> type : Profile::DataTypes::EventEnum :> type default type::MEASUREMENT_VALUE;
                attribute result [0..1] :>> result : Profile::DataTypes::double;
            }
            part def MeasurementUnits :> Event {
                doc /* {{def(EventEnum::MEASUREMENT_UNITS)}}*/
                constant attribute type :>> type : Profile::DataTypes::EventEnum :> type default type::MEASUREMENT_UNITS;
            }
            part def CharacteristicStatus :> Event {
                doc /* {{def(EventEnum::CHARACTERISTIC_STATUS)}}*/
                constant attribute type :>> type : Profile::DataTypes::EventEnum :> type default type::ADAPTER_URI;
                attribute result [0..1] :>> result : Profile::DataTypes::CharacteristicStatusEnum :> result;
            }
            part def UncertaintyType :> Event {
                doc /* {{def(EventEnum::UNCERTAINTY_TYPE)}}*/
                constant attribute type :>> type : Profile::DataTypes::EventEnum :> type default type::UNCERTAINTY_TYPE;
                attribute result [0..1] :>> result : Profile::DataTypes::UncertaintyTypeEnum;
            }
            part def Uncertainty :> Event {
                doc /* {{def(EventEnum::UNCERTAINTY)}}*/
                constant attribute type :>> type : Profile::DataTypes::EventEnum :> type default type::UNCERTAINTY;
                attribute result [0..1] :>> result : Profile::DataTypes::double;
            }
            connection def {
                end result :>> target::result : Profile::DataTypes::SensorAttachmentResult => target.result;
                private end : SensorAttachment;
            }
            part def AlarmLimits :> Event {
                doc /* {{def(EventEnum::ALARM_LIMITS)}}*/
                constant attribute type :>> type : Profile::DataTypes::EventEnum :> type default type::ALARM_LIMIT;
                part result [0..1] :>> result : Profile::DataTypes::AlarmLimitResult;
            }
            part def ControlLimits :> Event {
                doc /* {{def(EventEnum::CONTROL_LIMITS)}}*/
                constant attribute type :>> type : Profile::DataTypes::EventEnum :> type default type::CONTROL_LIMIT;
                part result [0..1] :>> result : Profile::DataTypes::ControlLimitResult;
            }
            part def SpecificationLimits :> Event {
                doc /* {{def(EventEnum::SPECIFICATION_LIMITS)}}*/
                constant attribute type :>> type : Profile::DataTypes::EventEnum :> type default type::SPECIFICATION_LIMIT;
                part result [0..1] :>> result : Profile::DataTypes::SpecificationLimitResult;
            }
            part def ToolCuttingItem :> Event {
                doc /* {{def(EventEnum::TOOL_CUTTING_ITEM)}}*/
                constant attribute type :>> type : Profile::DataTypes::EventEnum :> type default type::TOOL_CUTTING_ITEM;
            }
            part def 'Hardware.Model' :> Hardware {
                doc /* model info of the hardware or software.*/
                constant attribute subType :>> ActiveAxes::subType : Profile::DataTypes::DataItemSubTypeEnum :> ActiveAxes::subType default subType::MODEL;
            }
            part def LocationAddress :> Event {
                doc /* {{def(EventEnum::LOCATION_ADDRESS)}}*/
                constant attribute type :>> type : Profile::DataTypes::EventEnum :> type default type::LOCATION_ADDRESS;
                part result [0..1] :>> result : Profile::DataTypes::LocationAddressResult;
            }
            part def ActivePowerSource :> Event {
                doc /* {{def(EventEnum::ACTIVE_POWER_SOURCE)}}*/
                constant attribute type :>> type : Profile::DataTypes::EventEnum :> type default type::ACTIVE_POWER_SOURCE;
                attribute result [0..1] :>> result : Profile::DataTypes::string :> result {
                    doc /* name of the power source referring to {{block(Configuration)}} {{property(PowerSource::value)}}.*/
                }
            }
            part def LocationNarrative :> Event {
                doc /* {{def(EventEnum::LOCATION_NARRATIVE)}}*/
                constant attribute type :>> type : Profile::DataTypes::EventEnum :> type default type::LOCATION_NARRATIVE;
            }
            part def Thickness :> Event {
                doc /* {{def(EventEnum::THICKNESS)}}*/
                constant attribute type :>> type : Profile::DataTypes::EventEnum :> type default type::THICKNESS;
                constant attribute subType :>> subType : Profile::DataTypes::DataItemSubTypeEnum :> subType default subType::ACTUAL;
                attribute result [0..1] :>> result : Profile::DataTypes::float;
            }
            part def 'Thickness.Actual' :> Thickness {
                doc /* {{def(EventEnum::THICKNESS)}} that is {{def(DataItemSubTypeEnum::ACTUAL)}}.*/
                constant attribute subType [1] :>> ActiveAxes::subType : Profile::DataTypes::DataItemSubTypeEnum :> ActiveAxes::subType default subType::ACTUAL;
            }
            part def 'Thickness.Commanded' :> Thickness {
                doc /* {{def(EventEnum::THICKNESS)}} that is {{def(DataItemSubTypeEnum::COMMANDED)}}.*/
                constant attribute subType [1] :>> ActiveAxes::subType : Profile::DataTypes::DataItemSubTypeEnum :> ActiveAxes::subType default subType::COMMANDED;
            }
            part def 'Thickness.Target' :> Thickness {
                doc /* {{def(EventEnum::THICKNESS)}} that is {{def(DataItemSubTypeEnum::TARGET)}}.*/
                constant attribute subType [1] :>> ActiveAxes::subType : Profile::DataTypes::DataItemSubTypeEnum :> ActiveAxes::subType default subType::TARGET;
            }
            part def 'Thickness.Programmed' :> Thickness {
                doc /* {{def(EventEnum::THICKNESS)}} that is {{def(DataItemSubTypeEnum::PROGRAMMED)}}.*/
                constant attribute subType [1] :>> ActiveAxes::subType : Profile::DataTypes::DataItemSubTypeEnum :> ActiveAxes::subType default subType::PROGRAMMED;
            }
            part def LocationSpatialGeographic :> Event {
                doc /* {{def(EventEnum::LOCATION_SPATIAL_GEOGRAPHIC)}}*/
                constant attribute type :>> type : Profile::DataTypes::EventEnum :> type default type::LOCATION_SPATIAL_GEOGRAPHIC;
                part result [0..1] :>> result : Profile::DataTypes::LocationSpatialGeographicResult;
            }
            part def PartIndex :> Event {
                doc /* {{def(EventEnum::PART_INDEX)}}*/
                constant attribute type :>> type : Profile::DataTypes::EventEnum :> type default type::PART_INDEX;
                attribute result [0..1] :>> result : Profile::DataTypes::integer;
            }
            part def AssociatedAssetId :> Event {
                doc 
                /* {{def(EventEnum::ASSOCIATED_ASSET_ID)}}
                 *
                 * If defined as a DataSet or Table:
                 *
                 * * `key` **MUST** be an {{(block(Asset)}} type. Examples: CuttingTool, Fixture, File.
                 *
                 * * `value` **MUST** be the corresponding {{block(Asset::assetId)}}.*/
                constant attribute type :>> type : Profile::DataTypes::EventEnum :> type default type::ASSOCIATED_ASSET_ID;
            }
            part def AssetAdded :> Event {
                doc /* {{def(EventEnum::ASSET_ADDED)}}*/
                attribute assetType [0..1] : Profile::DataTypes::string {
                    doc /* type of {{block(Asset)}} added. See {{package(Asset Information Model)}} for details on the {{block(Asset)}} model.*/
                }
                constant attribute type :>> type : Profile::DataTypes::EventEnum :> type default type::ASSET_ADDED;
                attribute hash [0..1] : Profile::DataTypes::string {
                    doc /* condensed message digest from a secure one-way hash function. {{cite(FIPS PUB 180-4)}}*/
                }
            }
            part def TaskAssetId :> Event {
                doc /* {{def(EventEnum::TASK_ASSET_ID)}}*/
                constant attribute type :>> type : Profile::DataTypes::EventEnum :> type default type::TASK_ASSET_ID;
            }
            part def BindingState :> Event {
                doc /* {{def(EventEnum::BINDING_STATE)}}*/
                attribute result [0..1] :>> result : Profile::DataTypes::BindingStateEnum;
                constant attribute type :>> type : Profile::DataTypes::EventEnum :> type default type::BINDING_STATE;
            }
            part def 'Material.Electrode' :> MaterialLayer {
                doc /* {{def(EventEnum::MATERIAL)}} for an {{def(DataItemSubType::ELECTRODE)}}*/
                constant attribute subType :>> subType : Profile::DataTypes::DataItemSubTypeEnum :> subType default subType::ELECTRODE;
            }
            part def 'Material.Gas' :> MaterialLayer {
                doc /* {{def(EventEnum::MATERIAL)}} that is a {{def(DataItemSubType::GAS)}}*/
                constant attribute subType :>> subType : Profile::DataTypes::DataItemSubTypeEnum :> subType default subType::GAS;
            }
            part def 'Material.Filler' :> MaterialLayer {
                doc /* {{def(EventEnum::MATERIAL)}} that is a {{def(DataItemSubType::FILLER)}}*/
                constant attribute subType :>> subType : Profile::DataTypes::DataItemSubTypeEnum :> subType default subType::FILLER;
            }
            part def SwingAngle :> Event {
                doc /* {{def(EventEnum::SWING_ANGLE)}}*/
                constant attribute units :>> units : Profile::DataTypes::UnitEnum :> units default units::MILLIMETER;
                constant attribute type :>> Sample::type : Profile::DataTypes::EventEnum :> Sample::type default type::SWING_ANGLE;
                attribute result [0..1] :>> result : Profile::DataTypes::float;
            }
            part def SwingDiameter :> Event {
                doc /* {{def(EventEnum::SWING_DIAMETER)}}*/
                constant attribute units :>> units : Profile::DataTypes::UnitEnum :> units default units::MILLIMETER;
                constant attribute type :>> Sample::type : Profile::DataTypes::EventEnum :> Sample::type default type::SWING_DIAMETER;
                attribute result [0..1] :>> result : Profile::DataTypes::float;
            }
            part def SwingRadius :> Event {
                doc /* {{def(EventEnum::SWING_RADIUS)}}*/
                constant attribute units :>> units : Profile::DataTypes::UnitEnum :> units default units::MILLIMETER;
                constant attribute type :>> Sample::type : Profile::DataTypes::EventEnum :> Sample::type default type::SWING_RADIUS;
                attribute result [0..1] :>> result : Profile::DataTypes::float;
            }
            part def Depth :> Event {
                doc /* {{def(EventEnum::DEPTH)}}*/
                attribute result [0..1] :>> result : Profile::DataTypes::float;
                constant attribute type :>> type : Profile::DataTypes::EventEnum :> type default type::DEPTH;
                constant attribute units :>> units : Profile::DataTypes::UnitEnum :> units default units::MILLIMETER;
            }
            part def 'Depth.Plunge' :> Depth {
                doc /* {{def(EventEnum::DEPTH)}} when the action is to {{def(DataItemSubType::PLUNGE)}}*/
                constant attribute subType :>> subType : Profile::DataTypes::DataItemSubTypeEnum :> subType default subType::PLUNGE;
            }
            part def 'Depth.Peck' :> Depth {
                doc /* {{def(EventEnum::DEPTH)}} when the action is to {{def(DataItemSubType::PECK)}}*/
                constant attribute subType :>> subType : Profile::DataTypes::DataItemSubTypeEnum :> subType default subType::PECK;
            }
            part def 'Depth.Cut' :> Depth {
                doc /* {{def(EventEnum::DEPTH)}} when the action is to {{def(DataItemSubType::CUT)}}*/
                constant attribute subType :>> subType : Profile::DataTypes::DataItemSubTypeEnum :> subType default subType::CUT;
            }
            part def 'Depth.Layer' :> Depth {
                doc /* {{def(EventEnum::DEPTH)}} for a {{def(DataItemSubType::LAYER)}}*/
                constant attribute subType :>> subType : Profile::DataTypes::DataItemSubTypeEnum :> subType default subType::LAYER;
            }
            part def FixtureAssetId :> Event {
                doc /* {{def(EventEnum::FIXTURE_ASSET_ID)}}*/
                constant attribute type :>> type : Profile::DataTypes::EventEnum :> type default type::FIXTURE_ASSET_ID;
            }
            doc /* This section provides semantic information for {{block(Event)}} types.*/
        }
        package 'Condition Types' {
            part def Actuator :> Condition {
                doc /* {{def(ConditionEnum::ACTUATOR)}}*/
                constant attribute type [1] :>> type : Profile::DataTypes::ConditionEnum default type::ACTUATOR;
            }
            part def Communications :> Condition {
                doc /* {{def(ConditionEnum::COMMUNICATIONS)}}*/
                constant attribute type [1] :>> type : Profile::DataTypes::ConditionEnum default type::COMMUNICATIONS;
            }
            part def DataRange :> Condition {
                doc /* {{def(ConditionEnum::DATA_RANGE)}}*/
                constant attribute type [1] :>> type : Profile::DataTypes::ConditionEnum default type::DATA_RANGE;
            }
            part def LogicProgram :> Condition {
                doc /* {{def(ConditionEnum::LOGIC_PROGRAM)}}*/
                constant attribute type [1] :>> type : Profile::DataTypes::ConditionEnum default type::LOGIC_PROGRAM;
            }
            part def MotionProgram :> Condition {
                doc /* {{def(ConditionEnum::MOTION_PROGRAM)}}*/
                constant attribute type [1] :>> type : Profile::DataTypes::ConditionEnum default type::MOTION_PROGRAM;
            }
            part def System :> Condition {
                doc /* {{def(ConditionEnum::SYSTEM)}}*/
                constant attribute type [1] :>> type : Profile::DataTypes::ConditionEnum default type::SYSTEM;
            }
            doc 
            /* This section provides semantic information for {{block(Condition)}} types.
             *
             * {{block(Condition)}} types are reported differently from other {{block(Observation)}} types. They are reported based on the {{term(condition state)}} for each {{block(Condition)}}.
             *
             * The {{property(DataItem::type)}} and {{property(DataItem::subType)}} (where applicable) for a {{block(Condition)}} **MAY** be any of the {{property(DataItem::type)}} and {{property(DataItem::subType)}} defined for {{block(DataItem)}}s with {{property(DataItem::category)}} as `SAMPLE` or {{property(DataItem::category)}} as `EVENT` listed in the {{term(Device Information Model)}}.
             *
             * This section lists additional {{block(Condition)}} types that have been defined to represent the health and fault status of {{termplural(Component)}}.*/
        }
        doc 
        /* This section provides semantic information for the {{block(Observation)}} types.
         *
         * {{block(Observation)}} entities are instantiated as {{block(Sample)}}, {{block(Event)}} or {{block(Condition)}} entities based upon the {{property(DataItem::category)}} and {{property(DataItem::type)}} defined for the corresponding {{block(DataItem)}}.
         *
         * See {{figure(DeviceStream Example)}} for examples on how the {{block(Observation)}} types are organized within {{block(ComponentStream)}}.*/
    }
    part def DeviceStream {
        doc /* {{termplural(organize)}} data reported from a {{block(Device)}}.*/
        comment /* Description*/
        attribute name [1] : Profile::DataTypes::string {
            doc 
            /* name of the {{block(Device)}}.
             *
             * The value reported for {{property(DeviceStream::name)}} **MUST** be the same as the value defined for the {{property(Device::name)}} in the {{term(MTConnectDevices Response Document)}}.*/
        }
        attribute uuid [1] : Profile::DataTypes::UUID {
            doc /* uuid of the {{block(Device)}}.  The value reported for {{property(DeviceStream::uuid)}} **MUST** be the same as the value defined for the {{property(Device::uuid)}} of the same {{block(Device)}} in the {{term(MTConnectDevices Response Document)}}.*/
        }
        part hasComponentStream [1..*] : 'Observation Information Model'::ComponentStream;
        doc 
        /* {{block(DeviceStream)}} **MUST** be provided for each {{block(Device)}} reporting data in an {{term(MTConnectStreams Response Document)}}.
         *
         * If the response to the request for data from an {{term(agent)}} does not contain any data for a specific {{block(Device)}}, an empty {{block(DeviceStream)}} entity **MAY** be created to indicate that the {{block(Device)}} exists, but there was no data available.*/
    }
    connection def ComponentStream {
        end hasComponentStream : 'Observation Information Model'::ComponentStream => target.hasComponentStream;
        doc /* See {{sect(ComponentStream)}}.*/
        end : DeviceStream;
    }
    part def ComponentStream {
        doc /* organizes the data associated with each {{block(Component)}} entity defined for a {{block(Device)}} in the associated {{term(MTConnectDevices Response Document)}}.*/
        comment /* Description*/
        attribute component [1] : Profile::DataTypes::string {
            doc 
            /* identifies the {{block(Component)}} type associated with the {{block(ComponentStream)}}.
             *
             * Examples of {{property(ComponentStream::component)}} are {{block(Device)}}, {{block(Controller)}}, {{block(Linear)}} and {{block(Loader)}}.*/
        }
        attribute componentId [1] : Profile::DataTypes::ID {
            doc /* identifier of the {{block(Component)}} as defined by the {{property(Component::id)}} in the {{term(MTConnectDevices Response Document)}}.*/
        }
        attribute name [0..1] : Profile::DataTypes::string {
            doc /* name of the {{block(Component)}} associated with the {{block(ComponentStream)}}.*/
        }
        attribute nativeName [0..1] : Profile::DataTypes::string {
            doc /* common name of the {{block(Component)}} associated with the {{block(ComponentStream)}}.*/
        }
        attribute uuid [0..1] : Profile::DataTypes::UUID {
            doc /* uuid of the {{block(Component)}} associated with the {{block(ComponentStream)}}.*/
        }
        ref part organizesEvent [0..*] : Event;
        ref part organizesSample [0..*] : Sample;
        ref part organizesCondition [0..*] : Condition;
        private ref part isOrganizerFor [1] : 'Device Information Model'::Components::Component;
        doc /* At least one of {{block(Sample)}}, {{block(Event)}}, or {{block(Condition)}} **MUST** be organized by a {{block(ComponentStream)}} entity.*/
    }
    abstract part def Observation :> Glossary::'MTConnect Terms'::Observation {
        doc /* abstract entity that provides telemetry data for a {{block(DataItem)}} at a point in time.*/
        comment /* Description*/
        constant attribute compositionId [0..1] : Profile::DataTypes::ID {
            doc /* identifier of the {{block(Composition)}} entity defined in the {{term(MTConnectDevices Response Document)}} associated with the data reported for the {{block(Observation)}}.*/
        }
        constant attribute dataItemId [1] : Profile::DataTypes::ID {
            doc 
            /* unique identifier of the {{block(DataItem)}} associated with this {{block(Observation)}}.
             *
             * {{property(Observation::dataItemId)}} **MUST** match the associated {{property(DataItem::id)}} defined in the {{term(MTConnectDevices Response Document)}}.*/
        }
        constant attribute name [0..1] : Profile::DataTypes::string {
            doc 
            /* name of the {{block(DataItem)}} associated with this {{block(Observation)}}.
             *
             * {{property(Observation::name)}} **MUST** match the associated {{property(DataItem::name)}} defined in the {{term(MTConnectDevices Response Document)}}.*/
        }
        attribute sequence [1] : Profile::DataTypes::integer {
            doc 
            /* number representing the sequential position of an occurrence of an {{term(observation)}} in the data buffer of an {{term(agent)}}.
             *
             * {{property(Observation::sequence)}} **MUST** have a value represented as an unsigned 64-bit value from 1 to $$ 2^{64}-1 $$.*/
        }
        constant attribute subType [0..1] : Profile::DataTypes::DataItemSubTypeEnum {
            doc 
            /* subtype of the {{block(DataItem)}} associated with this {{block(Observation)}}.
             *
             * {{property(Observation::subType)}} **MUST** match the associated {{property(DataItem::subType)}} defined in the {{term(MTConnectDevices Response Document)}}.*/
        }
        attribute timestamp [1] : Profile::DataTypes::datetime {
            doc /* most accurate time available to a piece of equipment that represents the point in time that the data reported was measured.*/
        }
        private ref part madeByComponent [1] : 'Device Information Model'::Components::Component;
        constant attribute type [1] : Profile::DataTypes::DataItemTypeEnum {
            doc 
            /* type of the {{block(DataItem)}} associated with this {{block(Observation)}}.
             *
             * {{property(Observation::type)}} **MUST** match the associated {{property(DataItem::type)}} defined in the {{term(MTConnectDevices Response Document)}}.*/
        }
        constant attribute units [0..1] : Profile::DataTypes::UnitEnum {
            doc 
            /* units of the {{block(DataItem)}} associated with this {{block(Observation)}}.
             *
             * {{property(Observation::units)}} **MUST** match the associated {{property(DataItem::units)}} defined in the {{term(MTConnectDevices Response Document)}}.*/
        }
        attribute isUnavailable [1] : Profile::DataTypes::boolean default true {
            doc 
            /* when `true`, {{property(Observation::result)}} is indeterminate.
             *
             * > Note 1 to entry: In {{term(XML)}}, when `isUnavailable` is `true`, the {{term(XML)}} `CDATA` of the `Observation` **MUST** be `UNAVAILABLE`.
             *  ```xml
             * <Execution dataItemId="..." ...>UNAVAILABLE</Execution>
             * ```
             *
             * > Note 2 to entry: In {{term(JSON)}}, when `isUnavailable` is `true`, the {{term(JSON)}} `value` of the `Observation` **MUST** be `UNAVAILABLE`.
             * ```json
             *   "Execution" : [ { "dataItemId": "..." ..., "value": "UNAVAILABLE" } ]
             * ```*/
        }
        attribute result [0..1] : Profile::DataTypes::string {
            doc 
            /* {{term(observation)}} of the {{block(Observation)}} entity.
             *
             * The default value type for {{property(Observation::result)}} is `string`.
             *
             * > Note 1 to entry: in {{term(XML)}} the {{property(Observation::result)}} is the `CDATA` of the Observation {{term(element)}}.
             *
             * ~~~~xml
             * <Execution dataItemId="..." ...>READY</Execution>
             * ~~~~
             *
             * > Note 2 to entry: in {{term(JSON)}} the {{property(Observation::result)}} is the member `value` of the Observation object.
             *
             * ~~~~json
             * "Execution" : [ { "dataItemId": "..." ..., "value": "READY" } ]
             * ~~~~*/
        }
        private ref part madeForDataItem [1] : 'Device Information Model'::DataItems::DataItem;
        private attribute quality [0..1] : Profile::DataTypes::QualityEnum default quality::UNVERIFIABLE {
            doc /* indicates if the {{block(Observation)}} is verifiable and is in accordance with the normative definitions within the MTConnect Standard.*/
        }
        private attribute deprecated [0..1] : Profile::DataTypes::boolean default false {
            doc /* indicates if the {{block(Observation)}} has any property or controlled vocabulary that has been deprecated in the MTConnect Standard.*/
        }
        private attribute extended [0..1] : Profile::DataTypes::boolean default false {
            doc /* indicates if the {{block(Observation)}} has any property or controlled vocabulary that has been extended and cannot be validated.*/
        }
        doc 
        /* ![Observations](figures/Observations.png "Observations"){: width="0.8"}
         *
         * > Note: See {{sect(Observations Schema Diagrams)}} for XML schema. The XML schema also shows differences in XML representation of certain MTConnect entities.
         *
         * {{figure(DeviceStream Example)}} shows a complete example of {{block(DeviceStream)}} for the {{block(Device)}} shown in {{package(Device Information Model)}}.
         *
         * ![DeviceStream Example](figures/DeviceStream%20Example.png "DeviceStream Example"){: width="0.8"}
         *
         * > Note: See {{lst(devicestream-example)}} for the {{term(XML)}} representation of the same example.
         *
         *
         * This section provides semantic information for the {{block(Observation)}} model.
         *
         * > Note: See {{sect(Observations Schema Diagrams)}} for XML schema of {{block(Observation)}} types.
         *
         * #### Observations made for DataItem
         *
         * {{block(Component)}} {{termplural(observe)}} {{block(DataItem)}} entities and creates {{block(Observation)}} entities for the {{block(DataItem)}} entities. See {{figure(Observations)}}.
         *
         * {{block(Observation)}} entities made by a {{block(Component)}} are organized by a {{block(ComponentStream)}} which is specifically created for that {{block(Component)}}.
         *
         * ![Observations made for DataItem Example](figures/Observations%20made%20for%20DataItem%20Example.png "Observations made for DataItem Example"){: width="0.8"}
         *
         * > Note: See {{sect(Observations made for DataItem Example)}} for how XML representation of the same example is separated into {{term(MTConnectDevices Response Document)}} and {{term(MTConnectStreams Response Document)}}.
         *
         * {{figure(Observations made for DataItem Example)}} is a subset of {{figure(DeviceStream Example)}}. It shows an example of the association between a {{block(DataItem)}} {{block(Event)}} type (`EMERGENCY_STOP`) and an {{block(Observation)}} {{block(Event)}} type (`EmergencyStop`). See {{sect(Naming Convention for Observation types)}}.
         *
         * {{figure(Observations made for DataItem Example)}} also shows example of the association between a {{block(Component)}} type (`Controller`) and related {{block(ComponentStream)}}.
         *
         * #### Naming Convention for Observation types
         *
         * The name of an {{block(Observation)}} type **MUST** derive from the associated {{property(DataItem::type)}} converted to Pascal-Case by removing underscores (_ ) and capitalizing each word. The conversion **MUST NOT** apply to the following abbreviated words: `PH`, `AC`, `DC` and `URI`. `MTCONNECT` **MUST** be converted to `MTConnect`. See {{figure(Observations made for DataItem Example)}} for an example.
         *
         * The name of an {{block(Observation)}} type reported in the {{term(MTConnectStreams Response Document)}} is extended when the {{property(DataItem::representation)}} is used to further describe that {{block(DataItem)}} in the {{term(MTConnectDevices Response Document)}}. See {{package(Representations)}} for more details.*/
    }
    part def Sample :> Observation {
        doc /* {{block(Observation)}} that is continuously changing or analog data value.
         */
        comment /* Description*/
        attribute duration [0..1] : Profile::DataTypes::SECOND {
            doc 
            /* time-period over which the data was collected.
             *
             * {{property(Sample::duration)}} **MUST** be provided when the {{property(DataItem::statistic)}} is defined in the {{term(MTConnectDevices Response Document)}}.*/
        }
        attribute resetTriggered [0..1] : Profile::DataTypes::ResetTriggeredEnum {
            doc 
            /* identifies when a reported value has been reset and what has caused that reset to occur for those {{block(DataItem)}} entities that may be periodically reset to an initial value.
             *
             * `resetTriggered` **MUST** only be provided for the specific occurrence of a {{block(DataItem)}} reported in the {{term(MTConnectStreams Response Document)}} when the reset occurred.*/
        }
        attribute sampleRate [0..1] : Profile::DataTypes::float {
            doc /* rate at which successive samples of the value are recorded.
             */
            comment /* Description*/
            doc 
            /* {{property(Sample::sampleRate)}} is expressed in terms of samples per second.
             *
             * If {{property(Sample::sampleRate)}} is smaller than one, the number can be represented as a decimal type floating-point number. For example, a rate of 1 per 10 seconds would be 0.1 {{property(Sample::sampleRate)}} **MUST** be provided when {{property(DataItem::representation)}} defined in the {{term(MTConnectDevices Response Document)}} is `TIME_SERIES`.
             *
             * When {{property(DataItem::representation)}} is not `TIME_SERIES`, it **MUST** be assumed that the data reported is represented by a single value and {{property(Sample::sampleRate)}} **MUST NOT** be reported in the {{term(MTConnectStreams Response Document)}}.*/
        }
        attribute statistic [0..1] : Profile::DataTypes::StatisticEnum {
            doc /* type of statistical calculation defined by the {{property(DataItem::statistic)}} defined in the {{term(MTConnectDevices Response Document)}}.*/
        }
        private ref part organizedByComponentStream : 'Observation Information Model'::ComponentStream;
        attribute result [0..1] :>> result : Profile::DataTypes::float;
        constant attribute units [1] :>> units : Profile::DataTypes::UnitEnum;
        constant attribute type [1] :>> type : Profile::DataTypes::SampleEnum :> type;
        doc 
        /*
         * It provides the information and data reported from a piece of equipment for those {{block(DataItem)}} entities defined with {{property(DataItem::category)}} as `SAMPLE` in the {{term(MTConnectDevices Response Document)}}.
         *
         * {{block(Sample)}} **MUST** always be reported in `float`.
         *
         * {{figure(Sample Example)}} shows {{block(Sample)}} type examples. It also shows an example for when the {{property(Observation::result)}} is not available (`dataItemId`=`cspeed`).
         *
         * ![Sample Example](figures/Sample%20Example.png "Sample Example"){: width="0.8"}
         *
         * > Note: See {{lst(sample-example)}} for the {{term(XML)}} representation of the same example.
         *
         * The following {{sect(Value Properties of Sample)}} lists the additional and/or updated attributes for {{block(Sample)}}.*/
    }
    part def Event :> Observation {
        doc /* {{block(Observation)}} that is a discrete piece of information from a piece of equipment.
         */
        comment /* Description*/
        attribute resetTriggered [0..1] : Profile::DataTypes::ResetTriggeredEnum {
            doc 
            /* identifies when a reported value has been reset and what has caused that reset to occur for those {{block(DataItem)}} entities that may be periodically reset to an initial value.
             *
             * `resetTriggered` **MUST** only be provided for the specific occurrence of a {{block(DataItem)}} reported in the {{term(MTConnectStreams Response Document)}} when the reset occurred.*/
        }
        private ref part organizedByComponentStream : 'Observation Information Model'::ComponentStream;
        constant attribute type [1] :>> type : Profile::DataTypes::EventEnum;
        doc 
        /*
         * It provides the information and data reported from a piece of equipment for those {{block(DataItem)}} entities defined with {{property(DataItem::category)}} as `EVENT` in the {{term(MTConnectDevices Response Document)}}.
         *
         * {{figure(Event Example)}} shows {{block(Event)}} type examples. It also shows an example for when the {{property(Observation::result)}} is not available (`dataItemId`=`d1_asset_rem`).
         *
         * ![Event Example](figures/Event%20Example.png "Event Example"){: width="0.8"}
         *
         * > Note: See {{lst(event-example)}} for the {{term(XML)}} representation of the same example.
         *
         * The following {{sect(Value Properties of Event)}} lists the additional and/or updated attributes for {{block(Event)}}.*/
    }
    part def Condition :> Observation {
        doc 
        /* {{block(Observation)}} that provides the {{term(condition)}} of a piece of equipment or a {{term(Component)}}.
         *
         */
        comment /* Description*/
        attribute nativeCode [0..1] : Profile::DataTypes::string {
            doc /* native code is the proprietary identifier designating a specific alarm, fault or warning code provided by the piece of equipment.*/
        }
        attribute nativeSeverity [0..1] : Profile::DataTypes::string {
            doc /* severity information to a client software application if the piece of equipment designates a severity level to a fault.*/
        }
        attribute qualifier [0..1] : Profile::DataTypes::QualifierEnum {
            doc 
            /* additional information regarding a {{term(condition state)}} associated with the measured value of a process variable.
             *
             * {{property(Condition::qualifier)}} defines whether the {{term(condition state)}} represented indicates a measured value that is above or below an expected value of a process variable.*/
        }
        attribute statistic [0..1] : Profile::DataTypes::StatisticEnum {
            doc 
            /* {{property(Condition::statistic)}} provides additional information describing the meaning of the {{block(Condition)}} entity.
             *
             * {{property(Condition::statistic)}} **MUST** match the {{property(DataItem::statistic)}} defined in the {{term(MTConnectDevices Response Document)}}.*/
        }
        attribute 'xs:lang' [0..1] : Profile::DataTypes::xslang {
            doc 
            /* specifies the language of the {{property(Observation::result)}} returned for the {{block(Condition)}}. 
             *
             * See {{cite(IETF RFC 4646)}} (http://www.ietf.org/rfc/rfc4646.txt).*/
        }
        private ref part organizedByComponentStream : 'Observation Information Model'::ComponentStream;
        attribute 'state' [0..1] : Profile::DataTypes::ConditionStateEnum {
            doc /* {{term(condition state)}} of the piece of equipment or {{block(Component)}}.*/
        }
        constant attribute type [1] :>> type : Profile::DataTypes::ConditionEnum;
        attribute conditionId [1] : Profile::DataTypes::string {
            doc 
            /* identifier of an individual {{term(condition activation)}} provided by a piece of equipment.
             *
             * {{property(Condition::conditionId)}} **MUST** be unique for all concurrent {{termpl(condition activation)}}.
             *
             * {{property(Condition::conditionId)}} **MUST** be maintained for all state transitions related to the same {{term(condition activation)}}.
             *
             * Multiple {{property(Condition::conditionId)}}s **MAY** exist for the same {{property(nativeCode)}}.
             *
             * If {{property(Condition::conditionId)}} is not given, the value is the {{property(Condition::nativeCode)}}. If {{property(Condition::nativeCode)}} and {{property(Condition::conditionId)}} are not given, {{property(Condition::conditionId)}} **MUST** be generated.*/
        }
        doc 
        /* It provides the information and data reported from a piece of equipment with {{property(DataItem::category)}} as `CONDITION` in the {{term(MTConnectDevices Response Document)}}.
         *
         * {{figure(Condition Example)}} shows {{block(Condition)}} type examples for various {{property(Condition::state)}}: `Normal` (`dataItemId` = `path_system`) and `Warning` (`dataItemId` = `logic_cond`). It also shows an example for when the {{property(Condition::state)}} is not available (`dataItemId` = `cont_system`).
         *
         * ![Condition Example](figures/Condition%20Example.png "Condition Example"){: width="0.8"}
         *
         * > Note: See {{lst(condition-example)}} for the {{term(XML)}} representation of the same example.
         *
         * The following {{sect(Value Properties of Condition)}} lists the additional and/or updated attributes for {{block(Condition)}}.*/
    }
    doc 
    /* The {{term(Observation Information Model)}} provides a representation of the data reported by a piece of equipment used for a manufacturing process, or used for any other purpose.  Additional descriptive information associated with the reported data is defined by the {{block(MTConnectDevices)}} entity, which is described in {{package(Device Information Model)}}.
     *
     * Information defined in the {{term(Observation Information Model)}} allows a software application to (1) determine the {{termplural(Observation)}} for {{termplural(DataItem)}} returned from a piece of equipment and (2) interpret the data associated with those {{termplural(Observation)}} with the same meaning, value, and context that it had at its original source.  To do this, the software application issues one of two HTTP requests to an {{term(agent)}} associated with a piece of equipment.  They are:
     *
     * * `sample`:  Returns a designated number of time stamped {{termplural(Observation)}} from an {{term(agent)}} associated with a piece of equipment; subject to any HTTP filtering associated with the request.  See {{block(Agent)}} in {{package(Fundamentals)}} for details on the `sample` HTTP request.
     *
     * * `current`:  Returns a snapshot of either the most recent values or the values at a given sequence number for all {{termplural(Observation)}} associated with a piece of equipment from an {{term(agent)}}; subject to any HTTP filtering associated with the request.  See {{block(Agent)}} in {{package(Fundamentals)}} for details on the `current` HTTP request.
     *
     *
     * An {{term(agent)}} responds to either the `sample` or `current` HTTP request with an {{term(MTConnectStreams Response Document)}}.  This document contains information describing {{termplural(Observation)}} reported by an {{term(agent)}} associated with a piece of equipment.   A client software application may correlate the information provided in the {{term(MTConnectStreams Response Document)}} with the physical and logical structure for that piece of equipment defined in the {{block(MTConnectDevices)}} entity to form a clear and unambiguous understanding of the information provided.  (See details on the structure for a piece of equipment described in {{package(Device Information Model)}}).
     *
     * {{block(Streams)}} for an {{block(MTConnectStreams)}} entity contains a {{block(DeviceStream)}} entity for each piece of equipment represented in the document.  Each {{block(DeviceStream)}} is comprised of two primary types of entities – {{termplural(Component)}} and {{termplural(Observation)}}.  The contents of the {{block(DeviceStream)}} container are described in detail in this document, {{package(Observation Information Model)}} of the MTConnect Standard.
     *
     * {{termplural(Component)}} are defined for both the {{block(MTConnectDevices)}} and the {{block(MTConnectStreams)}} entities.  These {{termplural(Component)}} are used to provide a logical organization of the information provided in each entity.  
     *
     * * For an {{block(MTConnectDevices)}} entity: {{termplural(Component)}} organize information that represents the physical and logical parts and sub-parts of a piece of equipment.  (See {{block(Component)}} in {{package(Device Information Model)}} for more details on {{termplural(Component)}} used in the {{block(MTConnectDevices)}} entity).  
     *
     * * For an {{block(MTConnectStreams)}} entity: {{termplural(Component)}} provide the structure to organize the data returned from a piece of equipment and establishes the proper context for that data.  The {{termplural(Component)}} specifically defined for {{block(MTConnectStreams)}} are {{block(DeviceStream)}} (see {{sect(DeviceStream)}}) and {{block(ComponentStream)}} (see {{sect(ComponentStream)}}).   
     *
     * {{block(DeviceStream)}} and {{block(ComponentStream)}} entities have a direct correlation to each of the {{term(Component)}} defined in the {{block(MTConnectDevices)}} entity.
     *
     * Within each {{block(ComponentStream)}} entity in the {{block(MTConnectStreams)}} entity, {{termplural(Observation)}} are modeled as {{block(Observation)}} entities. The three types of {{block(Observation)}} entity are {{block(Sample)}}, {{block(Event)}}, and {{block(Condition)}}.  (See {{sect(Observation Types)}} for more information on these entities.)
     */
    comment /* Observations Appendix*/
    doc 
    /* {{newpage()}} 
     *
     * ## XML Schema Diagrams
     *
     * ### Observations Schema Diagrams
     *
     * See `Streams` element in `MTConnectStreams` schema.
     *
     * See `DeviceStream` element in `MTConnectStreams` schema.
     *
     * See `ComponentStream` element in `MTConnectStreams` schema.
     *
     * See `Sample` element in `MTConnectStreams` schema.
     *
     * See `Event` element in `MTConnectStreams` schema.
     *
     * See `Condition` element in `MTConnectStreams` schema.
     *
     * ### Representation Schema Diagrams
     *
     * See `AbsTimeSeries` element in `MTConnectStreams` schema.
     *
     * See `PartCountDiscrete` element in `MTConnectStreams` schema.
     *
     * See `VariableDataSet` element in `MTConnectStreams` schema.
     *
     * See `Entry` element in `MTConnectStreams` schema.
     *
     * See `WorkOffsetTable` element in `MTConnectStreams` schema.
     *
     * ## XML Examples
     *
     * ### DeviceStream Example
     *
     * ~~~~xml
     * <Streams>
     *   <DeviceStream name="M12346" uuid="M8010W4194N">
     *     <ComponentStream component="Device" name="M12346" componentId="d1">
     *       <Events>
     *         <Availability dataItemId="avail" sequence="156" timestamp="2021-10-01T14:26:38.668505Z">AVAILABLE</Availability>
     *         <AssetChanged assetType="CuttingTool" dataItemId="d1_asset_chg" sequence="75570" timestamp="2021-10-07T05:08:53.870206Z">M8010W4194N1.120</AssetChanged>
     *         <AssetRemoved assetType="CuttingTool" dataItemId="d1_asset_rem" sequence="140" timestamp="2021-10-01T11:40:08.101461Z">UNAVAILABLE</AssetRemoved>
     *       </Events>
     *     </ComponentStream>
     *     <ComponentStream component="Controller" name="controller" componentId="cont">
     *       <Events>
     *         <EmergencyStop dataItemId="estop" sequence="159" timestamp="2021-10-01T14:26:38.66869Z">ARMED</EmergencyStop>
     *       </Events>
     *       <Samples>
     *         <AccumulatedTime dataItemId="cut_time" sequence="75437" timestamp="2021-10-07T05:08:28.221704Z">1763070.0</AccumulatedTime>
     *       </Samples>
     *       <Condition>
     *         <Unavailable dataItemId="cont_system" sequence="72" timestamp="2021-10-11T21:04:03.251999Z" type="SYSTEM"/>
     *         <Warning dataItemId="cont_system" nativecode="313" nativeSeverity="50" sequence="75573" timestamp="2021-10-07T05:08:58.518317Z" type="LOGIC_PROGRAM">PALLET ARM DOWN RS. MALF.</Warning>
     *       </Condition>
     *     </ComponentStream>
     *     <ComponentStream component="Path" name="path" componentId="path1">
     *       <Events>
     *         <Execution dataItemId="execution" name="execution" sequence="222623" timestamp="2021-10-12T06:04:32.761198Z">INTERRUPTED</Execution>
     *         <VariableDataSet count="2" dataItemId="cvars" sequence="126513" timestamp="2021-10-12T03:57:31.106559Z">
     *           <Entry key="100">66.3314</Entry>
     *           <Entry key="101">167.2</Entry>
     *         </VariableDataSet>
     *         <WorkOffsetTable count="2" dataItemId="woffset" sequence="222101" timestamp="2021-10-12T06:04:11.990531Z">
     *           <Entry key="G53.1">
     *             <Cell key="X">1</Cell>
     *             <Cell key="Y">2</Cell>
     *             <Cell key="Z">3</Cell>
     *           </Entry>
     *           <Entry key="G53.2">
     *             <Cell key="X">4</Cell>
     *             <Cell key="Y">5</Cell>
     *             <Cell key="Z">6</Cell>
     *           </Entry>
     *         </WorkOffsetTable>
     *       </Events>
     *       <Samples>
     *         <CuttingSpeed dataItemId="cspeed" sequence="112" timestamp="2021-10-07T05:08:28.221704Z" subType="ACTUAL">UNAVAILABLE</CuttingSpeed>
     *       </Samples>
     *       <Condition>
     *         <Normal dataItemId="path_system" sequence="153" timestamp="2021-10-11T21:04:03.262845Z" type="SYSTEM"/>
     *       </Condition>
     *     </ComponentStream>
     *   </DeviceStream>
     * </Streams>
     * ~~~~
     * {: caption="DeviceStream Example"}
     *
     * ### Observations made for DataItem Example
     *
     * ~~~~xml
     * <Components>
     *   <Controller id="cont" name="controller">
     *       <DataItems>
     *       <DataItem category="EVENT" id="estop" name="estop" type="EMERGENCY_STOP"/>
     *     </DataItems>
     *   </Controller>
     * </Components>
     * ~~~~
     * {: caption="MTConnectDevices Response Document"}
     *
     * ~~~~xml
     * <ComponentStream component="Controller" name="controller" componentId="cont">
     *   <Events>
     *     <EmergencyStop dataItemId="estop" sequence="159" timestamp="2021-10-01T14:26:38.66869Z">ARMED</EmergencyStop>
     *   </Events>
     * </ComponentStream>
     * ~~~~
     * {: caption="MTConnectStreams Response Document"}
     *
     * ### Sample Example
     *
     * ~~~~xml
     * <Samples>
     *   <AccumulatedTime dataItemId="cut_time" sequence="75437" timestamp="2021-10-07T05:08:28.221704Z">1763070.0</AccumulatedTime>
     *   <CuttingSpeed dataItemId="cspeed" sequence="112" timestamp="2021-10-07T05:08:28.221704Z" subType="ACTUAL">UNAVAILABLE</CuttingSpeed>
     * </Samples>
     * ~~~~
     * {: caption="Sample Example"}
     *
     * ### Event Example
     *
     * ~~~~xml
     * <Events>
     *   <Availability dataItemId="avail" sequence="156" timestamp="2021-10-01T14:26:38.668505Z">AVAILABLE</Availability>
     *   <AssetRemoved assetType="CuttingTool" dataItemId="d1_asset_rem" sequence="140" timestamp="2021-10-01T11:40:08.101461Z">UNAVAILABLE</AssetRemoved>
     * </Events>
     * ~~~~
     * {: caption="Event Example"}
     *
     * ### Condition Example
     *
     * {{block(Condition)}} types are represented differently in {{term(XML)}} when compared to {{block(Sample)}} and {{block(Event)}} types. The element name is the {{term(condition state)}} of the {{block(Condition)}} type in Pascal Case. The name of the {{block(Condition)}} type is represented by the attribute `type`.
     *
     * If the {{term(condition state)}} is unavailable then the element name is represented by `Unavailable`.
     *
     * ~~~~xml
     * <Condition>
     *   <Unavailable dataItemId="cont_system" sequence="72" timestamp="2021-10-11T21:04:03.251999Z" type="SYSTEM"/>
     *   <Normal dataItemId="path_system" sequence="153" timestamp="2021-10-11T21:04:03.262845Z" type="SYSTEM"/>
     *   <Warning dataItemId="cont_system" nativecode="313" nativeSeverity="50" sequence="75573" timestamp="2021-10-07T05:08:58.518317Z" type="LOGIC_PROGRAM">PALLET ARM DOWN RS. MALF.</Warning>
     * </Condition>
     * ~~~~
     * {: caption="Condition Example"}
     *
     * ### DataSet Example
     *
     * ~~~~xml
     * <Events>
     *   <VariableDataSet count="2" dataItemId="cvars" sequence="126513" timestamp="2021-10-12T03:57:31.106559Z">
     *     <Entry key="100">66.3314</Entry>
     *     <Entry key="101">167.2</Entry>
     *   </VariableDataSet>
     * </Events>
     * ~~~~
     * {: caption="DataSet Example"}
     *
     * ### Table Example
     *
     * ~~~~xml
     * <Events>
     *   <WorkOffsetTable count="2" dataItemId="woffset" sequence="222101" timestamp="2021-10-12T06:04:11.990531Z">
     *     <Entry key="G53.1">
     *       <Cell key="X">1</Cell>
     *       <Cell key="Y">2</Cell>
     *       <Cell key="Z">3</Cell>
     *     </Entry>
     *     <Entry key="G53.2">
     *       <Cell key="X">4</Cell>
     *       <Cell key="Y">5</Cell>
     *       <Cell key="Z">6</Cell>
     *     </Entry>
     *   </WorkOffsetTable>
     * </Events>
     * ~~~~
     * {: caption="Table Example"}*/
}
package Glossary {
    connection def {
        end :>> Glossary::'Industrial Terms'::observation::'made for' : 'MTConnect Terms'::DataItem => 'has observation'.Glossary::'MTConnect Terms'::Observation::'made for';
        end :>> Glossary::'Industrial Terms'::observable::'has observation' : 'MTConnect Terms'::Observation => 'made for'.Glossary::'MTConnect Terms'::DataItem::'has observation';
    }
    dependency 
            from 'MTConnect Terms'::'Additional Observation Terms'::'Observed Event'
            to 'MTConnect Terms'::'Additional Observation Terms'::'Observed Condition';

    connection def {
        end 'made by' : 'Industrial Terms'::'engineered system' => 'made observation'.Glossary::'MTConnect Terms'::Observation::'made by';
        end 'made observation' : 'MTConnect Terms'::Observation => 'made by'.Glossary::'Industrial Terms'::'engineered system'::'made observation';
    }
    connection def 'made by' {
        end :>> Glossary::'Industrial Terms'::observation::'made by' : 'MTConnect Terms'::Component :> Glossary::'MTConnect Terms'::Observation::'made by' => target.Glossary::'MTConnect Terms'::Observation::'made by';
        private end : 'MTConnect Terms'::Observation;
    }
    dependency from 'MTConnect Terms'::Observation to 'MTConnect Terms'::Component;
    occurrence def adapter :> application {
        doc /* optional piece of hardware or software that transforms information provided by a piece of equipment into a form that can be received by an {{term(agent)}}.*/
    }
    occurrence def agent :> application {
        doc /* software that collects data published from one or more piece(s) of equipment, organizes that data in a structured manner, and responds to requests for data from client software systems by providing a structured response in the form of a {{term(response document)}} that is constructed using the {{term(semantic data model)}} of a Standard. 
         */
    }
    occurrence def 'alarm limit' {
        doc /* limit used to trigger warning or alarm indicators.*/
    }
    occurrence def application {
        doc 
        /* software or a program that is specific to the solution of an application problem.
         * {{cite(ISO/IEC 20944-1:2013)}}*/
    }
    occurrence def archetype :> 'Industrial Terms'::asset {
        doc /* {{term(archetype)}} provides the requirements, constraints, and common properties for a type of {{term(Asset)}}.*/
    }
    occurrence def 'asset buffer' {
        doc /* {{term(buffer)}} for {{termplural(Asset)}}.*/
    }
    occurrence def attachment {
        doc /* connection by which one thing is associated with another.*/
    }
    occurrence def buffer {
        doc /* section of an {{term(agent)}} that provides storage for information published from pieces of equipment.*/
    }
    occurrence def client :> application {
        doc 
        /* {{term(application)}} that sends {{term(request)}} for information to an {{term(agent)}}.
         *
         * > Note: Examples include software applications or a function that implements the {{term(request)}} portion of an {{term(interface)}} {{term(interaction model)}}.
         *
         */
    }
    occurrence def 'controlled vocabulary' {
        doc /* restricted set of values for a given property.*/
    }
    occurrence def 'data dictionary' {
        doc /* listing of standardized terms and definitions used in {{term(MTConnect Information Model)}}.*/
    }
    occurrence def 'data model' {
        doc /* organizes elements of data and standardizes how they relate to one another and to the properties of real-world entities.*/
    }
    occurrence def 'data set' {
        doc /* {{termplural(key-value pair)}} where each entry is uniquely identified by the {{term(key)}}.*/
    }
    occurrence def 'data source' {
        doc /* piece of equipment that can produce data that is published to an {{term(agent)}}.
         */
    }
    occurrence def deprecated {
        doc /* indication that specific content in an {{term(MTConnect Document)}} is currently usable but is regarded as being obsolete or superseded. */
    }
    occurrence def 'deprecation warning' {
        doc /* indication that specific content in an {{term(MTConnect Document)}} may be changed to {{term(deprecated)}} in a future release of the standard.*/
    }
    occurrence def document {
        doc /* piece of written, printed, or electronic matter that provides information or evidence that serves as an official record.*/
    }
    occurrence def 'electric current' {
        doc /* rate of flow of electric charge.*/
    }
    occurrence def extensible {
        doc /* ability for an implementer to extend {{term(MTConnect Information Model)}} by adding content not currently addressed in the MTConnect Standard.
         */
    }
    occurrence def force {
        doc /* push or pull on a mass which results in an acceleration.*/
    }
    occurrence def implementation {
        doc /* specific instantiation of the MTConnect Standard.*/
    }
    occurrence def 'information model' {
        doc /* rules, relationships, and terminology that are used to define how information is structured.*/
    }
    occurrence def instance {
        doc /* describes a set of {{term(streaming data)}} in an {{term(agent)}}.  Each time an {{term(agent)}} is restarted with an empty {{term(buffer)}}, data placed in the {{term(buffer)}} represents a new {{term(instance)}} of the {{term(agent)}}.*/
    }
    occurrence def 'interaction model' {
        doc /* model that defines how information is exchanged across an {{term(interface)}} to enable interactions between independent systems.*/
    }
    occurrence def 'interface' {
        doc /* means by which communication is achieved between independent systems.*/
    }
    occurrence def key {
        doc /* unique identifier in a {{term(key-value pair)}} association.*/
    }
    occurrence def 'key-value pair' {
        doc /* association between an identifier referred to as the {{term(key)}} and a value which taken together create a {{term(key-value pair)}}. */
    }
    occurrence def 'lower camel case' {
        doc /* first word is lowercase and the remaining words are capitalized and all spaces between words are removed.*/
    }
    occurrence def 'lower limit' {
        doc /* lower conformance boundary for a variable.*/
    }
    occurrence def 'lower warning' {
        doc /* lower boundary indicating increased concern and supervision may be required.*/
    }
    occurrence def major {
        doc /* identifier representing a consistent set of functionalities defined by the MTConnect Standard.*/
    }
    occurrence def maximum {
        doc /* numeric upper constraint.*/
    }
    occurrence def 'message' {
        doc /* communication in writing, in speech, or by signals.*/
    }
    occurrence def 'metadata' {
        doc 
        /* data that provides information about other data.
         *
         */
    }
    occurrence def minimum {
        doc /* numeric lower constraint.*/
    }
    occurrence def minor {
        doc /* identifier representing a specific set of functionalities defined by the MTConnect Standard.*/
    }
    occurrence def nominal {
        doc /* ideal or desired value for a variable.*/
    }
    occurrence def organize {
        doc /* act of containing and owning one or more elements.*/
    }
    occurrence def organizer {
        doc /* entity that {{termplural(organize)}} one or more elements.*/
    }
    occurrence def parameter {
        doc /* variable that must be given a value during the execution of a program or a communications command.*/
    }
    occurrence def 'part' {
        doc /* discrete item that has both defined and measurable physical characteristics including mass, material, and features, and is created by applying one or more manufacturing process steps to material*/
    }
    occurrence def 'pascal case' {
        doc /* first letter of each word is capitalized and the remaining letters are in lowercase. All space is removed between letters*/
    }
    occurrence def persistence {
        doc /* method for retaining or restoring information.*/
    }
    occurrence def requester {
        doc /* entity that initiates a {{term(request)}} for information in a communications exchange.*/
    }
    occurrence def reset {
        doc 
        /* act of reverting back the accumulated value or statistic to their initial value.
         *
         * > Note: An {{term(Observation)}} with a {{term(data set)}} representation removes all {{termplural(key-value pair)}}, setting the {{term(data set)}} to an empty set.
         *
         */
    }
    occurrence def responder {
        doc /* entity that responds to a {{term(request)}} for information in a communications exchange.*/
    }
    occurrence def 'response document' :> 'Protocol Terms'::'MTConnect Response Document' {
        doc /* electronic {{term(document)}} published by an {{term(MTConnect Agent)}} in response to a {{term(probe request)}}, {{term(current request)}}, {{term(sample request)}} or {{term(asset request)}}.*/
    }
    occurrence def patch {
        doc /* supplemental identifier representing only organizational or editorial changes to a {{term(minor)}} version document with no changes in the functionality described in that document.*/
    }
    occurrence def schema {
        doc /* definition of the structure, rules, and vocabularies used to define the information published in an electronic document.*/
    }
    occurrence def 'semantic data model' {
        doc /* methodology for defining the structure and meaning for data in a specific logical way that can be interpreted by a software system. */
    }
    occurrence def 'sensing element' {
        doc /* mechanism that provides a signal or measured value.*/
    }
    occurrence def 'sequence number' {
        doc /* primary key identifier used to manage and locate a specific piece of {{term(streaming data)}} in an {{term(agent)}}.*/
    }
    occurrence def 'specification limit' {
        doc /* limit defining a range of values designating acceptable performance for a variable.*/
    }
    occurrence def spindle {
        doc 
        /* mechanism that provides rotational capabilities to a piece of equipment. 
         *
         * > Note: Typically used for either work holding, materials or cutting tools.
         *
         */
    }
    occurrence def 'standard' {
        doc /* {{term(document)}} established by consensus that provides rules, guidelines, or characteristics for activities or their results.. {{cite(ISO/IEC Guide 2:2004)}}*/
    }
    occurrence def subtype {
        doc /* secondary or subordinate type of categorization or classification of information.*/
    }
    occurrence def table {
        doc /* two dimensional set of values given by a set of {{termplural(key-value pair)}} {{termplural(table entry)}}. */
    }
    occurrence def 'table cell' {
        doc /* subdivision of a {{term(table entry)}} representing a singular value.*/
    }
    occurrence def 'table entry' {
        doc /* subdivision of a {{term(table)}} containing a set of {{termplural(key-value pair)}} representing {{termplural(table cell)}}.*/
    }
    occurrence def type {
        doc /* classification or categorization of information.*/
    }
    occurrence def 'upper limit' {
        doc /* upper conformance boundary for a variable.*/
    }
    occurrence def 'upper warning' {
        doc /* upper boundary indicating increased concern and supervision may be required.*/
    }
    occurrence def version {
        doc /* unique identifier of the administered item. {{cite(ISO/IEC 11179-:2015)}}*/
        private ref occurrence __unnamed3 [1] : major;
        ref occurrence __unnamed5 [0..1] : patch;
        private ref occurrence __unnamed4 [0..1] : minor;
    }
    connection def {
        end : major => target.Glossary::version::__unnamed3;
        private end : version;
    }
    connection def {
        end : minor => target.Glossary::version::__unnamed4;
        private end : version;
    }
    connection def {
        end : patch => target.__unnamed5;
        private end : version;
    }
    package 'XML Terms' {
        occurrence def namespace {
            doc /* organizes information into logical groups.*/
        }
        occurrence def 'XML Schema' :> schema {
            doc /* {{term(schema)}} defining a specific document encoded in XML.
             */
        }
        occurrence def 'root element' :> element {
            doc /* first {{term(structural element)}} provided in a {{term(response document)}} encoded using XML. */
        }
        occurrence def 'document body' {
            doc /* portion of the content of an {{term(MTConnect Response Document)}} that is defined by the relative {{term(MTConnect Information Model)}}. The {{term(document body)}} contains the {{termplural(structural element)}} and {{termplural(Observation)}} or {{termplural(DataItem)}} reported in a {{term(response document)}}.
             */
        }
        occurrence def 'XML Document' :> document {
            doc /* structured text file encoded using {{term(XML)}}.*/
            private ref occurrence 'has document header' [0..1] : 'document header';
            private ref occurrence 'has document body' [0..1] : 'document body';
            private ref occurrence 'has namespace' [0..1] : namespace;
            private ref occurrence 'has xml schema' [0..1] : 'XML Schema';
        }
        occurrence def 'document header' {
            doc /* portion of the content of an {{term(MTConnect Response Document)}} that provides information from an {{term(agent)}} defining version information, storage capacity, protocol, and other information associated with the management of the data stored in or retrieved from the {{term(agent)}}.
             */
        }
        connection def {
            end 'has document header' : 'document header' => target.Glossary::'XML Terms'::'XML Document'::'has document header';
            private end : 'XML Document';
        }
        connection def {
            end 'has document body' : 'document body' => target.Glossary::'XML Terms'::'XML Document'::'has document body';
            private end : 'XML Document';
        }
        connection def {
            end 'has namespace' : namespace => target.Glossary::'XML Terms'::'XML Document'::'has namespace';
            private end : 'XML Document';
        }
        connection def {
            end 'has xml schema' : 'XML Schema' => target.Glossary::'XML Terms'::'XML Document'::'has xml schema';
            private end : 'XML Document';
        }
        occurrence def 'attribute' {
            doc /* additional information or property for an {{term(element)}}.
             */
        }
        occurrence def 'abstract element' :> element {
            doc 
            /* element that defines a set of common characteristics that are shared by a group of elements. An abstract entity cannot appear in a document. In a specific implementation, an abstract entity is replaced by a derived element that is itself not an abstract entity. The characteristics for the derived element are inherited from the abstract entity. 
             *
             */
        }
        occurrence def 'child element' :> element {
            doc /* {{term(element)}} of a data modeling structure that illustrates the relationship between itself and the higher-level {{term(parent element)}} within which it is contained.*/
        }
        occurrence def 'parent element' :> element {
            doc /* {{term(element)}} of a data modeling structure that illustrates the relationship between itself and the lower-level {{term(child element)}}.*/
        }
        occurrence def 'structural element' {
            doc /* {{term(element)}} that organizes information that represents the physical and logical parts and sub-parts of a piece of equipment.*/
        }
        occurrence def 'element name' {
            doc /* descriptive identifier contained in both the `start-tag` and `end-tag` of an XML element that provides the name of the element.*/
        }
    }
    package 'HTTP Terms' {
        occurrence def 'HTTP Status Code' {
            doc /* 3-digit integer result code of the attempt to understand and satisfy the request.  {{cite(IETF:RFC-2616)}}*/
        }
        occurrence def 'HTTP Server' {
            doc /* server that accepts {{term(HTTP Request)}} from {{term(client)}} and publishes {{term(HTTP Response)}} as a reply to those {{term(HTTP Request)}}. {{cite(IETF:RFC-2616)}}*/
        }
        occurrence def 'HTTP Body' {
            doc /* data bytes transmitted in an HTTP transaction message immediately following the headers. {{cite(IETF:RFC-2616)}}*/
        }
        occurrence def 'HTTP Header Field' {
            doc /* components of the header section of request and response messages in an HTTP transaction. {{cite(IETF:RFC-2616)}}*/
        }
        occurrence def 'HTTP Request URI' {
            doc /* Uniform Resource Identifier that identifies the resource upon which to apply the request. {{cite(IETF:RFC-2616)}}*/
        }
        occurrence def 'HTTP Request Method' {
            doc /* indicates the method to be performed on the resource identified by the Request-URI. {{cite(IETF:RFC-2616)}}*/
        }
        occurrence def 'HTTP Response' {
            doc 
            /* after receiving and interpreting a request message, a server responds with an HTTP response message. {{cite(IETF:RFC-2616)}}
             *
             * > Note: In MTConnect Standard, the information published from an {{term(agent)}} in reply to an {{term(HTTP Request)}}. 
             *
             */
        }
        occurrence def 'HTTP Messaging' {
            doc /* {{term(interface)}} for information exchange functionality. {{cite(IETF:RFC-2616)}}*/
        }
        occurrence def 'HTTP Request' :> 'Protocol Terms'::request {
            doc 
            /* request message from a client to a server includes, within the first line of that message, the method to be applied to the resource, the identifier of the resource, and the protocol version in use. {{cite(IETF:RFC-2616)}}
             *
             * > Note: In MTConnect Standard, a request issued by a {{term(client)}} to an {{term(agent)}} requesting information defined in the {{term(HTTP Request Line)}}.
             *
             */
        }
        occurrence def 'HTTP Query' {
            doc /* portion of a request for information that more precisely defines the specific information to be published in response to the request. {{cite(IETF:RFC-2616)}}*/
        }
        occurrence def 'HTTP Version' {
            doc /* version of the HTTP protocol. {{cite(IETF:RFC-2616)}}*/
        }
        occurrence def 'HTTP Message' {
            doc 
            /* consist of requests from client to server and responses from server to client. {{cite(IETF:RFC-2616)}}
             *
             * > Note: In MTConnect Standard, it describes the information that is exchanged between an {{term(agent)}} and a {{term(client)}}.
             *
             */
        }
        occurrence def 'HTTP Header' {
            doc /* header of either an {{term(HTTP Request)}} from a {{term(client)}} or an {{term(HTTP Response)}} from an {{term(agent)}}. {{cite(IETF:RFC-2616)}}*/
        }
        occurrence def 'HTTP Error Message' {
            doc /* response provided by an {{term(agent)}} indicating that an {{term(HTTP Request)}} is incorrectly formatted or identifies that the requested data is not available from the {{term(agent)}}.  {{cite(IETF:RFC-2616)}}*/
        }
        occurrence def 'HTTP Request Line' {
            doc 
            /* begins with a method token, followed by the Request-URI and the protocol version, and ending with CRLF. A CRLF is allowed in the definition of TEXT only as part of a header field continuation. {{cite(IETF:RFC-2616)}}
             *
             * > Note: the first line of an {{term(HTTP Request)}} describing a specific {{term(response document)}} to be published by an {{term(agent)}}.
             *
             */
        }
        occurrence def 'HTTP Method' {
            doc /* portion of a command in an {{term(HTTP Request)}} that indicates the desired action to be performed on the identified resource; often referred to as verbs. {{cite(IETF:RFC-2616)}}
             */
        }
    }
    package 'MTConnect Terms' {
        package 'Additional Observation Terms' {
            occurrence def 'Observed Measurement' :> Sample, Observation;
            occurrence def 'Observed Condition' :> Observation;
            occurrence def 'Observable Event' {
                attribute units [0..1] : Profile::DataTypes::string;
            }
            occurrence def 'Observable Sample';
            occurrence def 'Observed State' :> 'Observed Event';
            occurrence def 'Observed Normal' :> 'Observed Condition';
            occurrence def 'Observable Condition';
            occurrence def 'Observed Event' :> Observation, 'MTConnect Event';
            occurrence def 'Observable Measurement' :> 'Observable Sample' {
                attribute units [1] : Profile::DataTypes::string;
            }
            occurrence def 'Observable State' :> 'Observable Event';
            occurrence def 'Observed Fault' :> 'Observed Condition';
            occurrence def 'Observed Warning' :> 'Observed Condition';
            dependency from 'Observed Event' to 'Observed Measurement';
            occurrence def Event {
                doc /* Something that happens or takes place.*/
            }
            occurrence def Sample {
                doc /* The collection of one or more pieces of information.  
                 */
                attribute result [0..1] : Profile::DataTypes::float;
            }
            occurrence def Condition :> 'Observed Condition' {
                doc /* An indicator of the ability of a piece of equipment or {{term(Component)}} to function to specification.*/
            }
        }
        occurrence def Component :> Glossary::'Industrial Terms'::Thing, 'Industrial Terms'::'engineered system' {
            doc /* {{term(engineered system)}}  part of a {{term(Device)}} composed of zero or more {{termplural(Component)}}*/
            ref occurrence 'has component' [0..*] :>> Glossary::'Industrial Terms'::'engineered system'::'has part' : Component {
                doc /* a component relationship that inheres other components.*/
            }
            ref occurrence 'belongs to' [1] : Component :> Glossary::'Industrial Terms'::'engineered system'::'part of' {
                doc /* the owner of a component. a device may not belong to any other component.*/
            }
            private ref occurrence observes [0..*] : DataItem;
            private ref occurrence 'has configuration' [0..*] : Configuration;
            private ref occurrence 'has composition' [0..*] : Composition;
            private ref occurrence __unnamed7 [0] : Device :> 'has component';
            private ref occurrence [0..*] :>> Glossary::'Industrial Terms'::'engineered system'::'makes observation' : Observation;
        }
        occurrence def 'MTConnect Agent' :> agent {
            doc /* {{term(agent)}} for the {{term(MTConnect Information Model)}}.*/
        }
        occurrence def Asset :> 'Industrial Terms'::asset {
            doc 
            /* {{term(asset)}} that is used by the manufacturing process to perform tasks.
             *
             * > Note 1 to entry: An {{term(Asset)}} relies upon an {{term(Device)}} to provide {{termplural(observation)}} and information about itself and the {{term(Device)}} revises the information to reflect changes to the {{term(Asset)}} during their interaction. Examples of {{termplural(Asset)}} are cutting tools, Part Information, Manufacturing Processes, Fixtures, and Files.
             *
             * > Note 2 to entry: A singular {{property(Asset::assetId)}} uniquely identifies an {{term(Asset)}} throughout its lifecycle and is used to track and relate the {{term(Asset)}} to other {{termplural(Device)}} and entities.
             *
             * > Note 3 to entry: {{termplural(Asset)}} are temporally associated with a device and can be removed from the device without damage or alteration to its primary functions.
             *
             */
            private ref occurrence 'belongs to' [1] : Device;
        }
        occurrence def Composition :> Component {
            doc /* {{term(Component)}} belonging to a {{term(Component)}} and not composed of any {{termplural(Component)}}.*/
            private ref occurrence 'belongs to' [1] : Component;
            private ref occurrence __unnamed6 [0] : Component :> 'has component';
        }
        occurrence def 'MTConnect Document' :> document {
            doc /* {{term(document)}} that represents a Part(s) of the MTConnect Standard.*/
        }
        occurrence def Configuration :> 'Industrial Terms'::configuration {
            doc /* {{term(configuration)}} for a {{term(Component)}}*/
            private ref occurrence 'configuration for' [1] : Component;
        }
        occurrence def Device :> Component {
            doc /* {{term(Component)}} not belonging to any {{term(Component)}} that may have {{termplural(asset)}}*/
            private ref occurrence 'has asset' [0..*] : Asset;
            private ref occurrence __unnamed8 [0] : Component :> 'belongs to';
        }
        occurrence def 'MTConnect Interface' {
            doc /* {{term(interaction model)}} for interoperability between pieces of equipment.*/
        }
        occurrence def Observation :> Glossary::'Industrial Terms'::Thing, 'Industrial Terms'::observation {
            doc /* {{term(observation)}} that provides telemetry data for a {{term(DataItem)}}.*/
            private ref occurrence [1] :>> Glossary::'Industrial Terms'::observation::'made for' : DataItem;
            private ref occurrence 'made by' [1] : 'Industrial Terms'::'engineered system';
            private ref occurrence [1] :>> Glossary::'Industrial Terms'::observation::'made by' : Component :> 'made by';
            private ref occurrence [1] :>> Glossary::'Industrial Terms'::observation::'made by' : Component;
        }
        occurrence def 'MTConnect Event' :> 'Additional Observation Terms'::Event {
            doc /* {{term(observation)}} of either a state or discrete value of the {{term(Component)}}. */
        }
        connection def {
            end 'has component' :>> Glossary::'Industrial Terms'::'engineered system'::'has part' : Component => 'belongs to'.'has component';
            end 'belongs to' : Component :> Glossary::'Industrial Terms'::'engineered system'::'part of' => 'has component'.'belongs to';
        }
        connection def {
            end 'has configuration' : Configuration => 'configuration for'.Glossary::'MTConnect Terms'::Component::'has configuration';
            end 'configuration for' : Component => 'has configuration'.Glossary::'MTConnect Terms'::Configuration::'configuration for';
        }
        connection def {
            end 'belongs to' : Device => 'has asset'.Glossary::'MTConnect Terms'::Asset::'belongs to';
            end 'has asset' : Asset => 'belongs to'.Glossary::'MTConnect Terms'::Device::'has asset';
        }
        connection def {
            end 'observed by' : Component => observes.Glossary::'MTConnect Terms'::DataItem::'observed by';
            end observes : DataItem => 'observed by'.Glossary::'MTConnect Terms'::Component::observes;
        }
        connection def {
            end 'has composition' : Composition => 'belongs to'.Glossary::'MTConnect Terms'::Component::'has composition';
            end 'belongs to' : Component => 'has composition'.Glossary::'MTConnect Terms'::Composition::'belongs to';
        }
        dependency from Device to Composition;
        connection def {
            end : Component :> source::'has component' => target.Glossary::'MTConnect Terms'::Composition::__unnamed6;
            private end : Composition;
        }
        dependency from Asset to Device;
        connection def {
            end : Device :> source::'has component' => target.Glossary::'MTConnect Terms'::Component::__unnamed7;
            end : Component :> source::'belongs to' => source.Glossary::'MTConnect Terms'::Device::__unnamed8;
        }
        occurrence def DataItem :> 'Industrial Terms'::observable, 'Device Information Model'::DataItems::DataItem {
            doc /* {{term(observable)}} observed by a {{term(Component)}} that may make {{termplural(Observation)}}*/
            private ref occurrence 'observed by' [1] : Component;
            private ref occurrence [0..*] :>> Glossary::'Industrial Terms'::observable::'has observation' : Observation;
        }
        connection def {
            end :>> Glossary::'Industrial Terms'::'engineered system'::'makes observation' : Observation => 'made by'.Glossary::'MTConnect Terms'::Component::'makes observation';
            end :>> Glossary::'Industrial Terms'::observation::'made by' : Component => 'makes observation'.Glossary::'MTConnect Terms'::Observation::'made by';
        }
    }
    package 'Information Model Terms' {
        occurrence def 'Error Information Model' :> 'MTConnect Information Model' {
            doc /* {{term(information model)}} that describes the {{term(response document)}} returned by an {{term(agent)}} when it encounters an error while interpreting a {{term(request)}} for information from a {{term(client)}} or when an {{term(agent)}} experiences an error while publishing the {{term(response)}} to a {{term(request)}} for information.*/
            private ref occurrence __unnamed11 [0..*] : 'Protocol Terms'::'MTConnectErrors Response Document';
        }
        occurrence def 'Asset Information Model' :> 'MTConnect Information Model' {
            doc /* {{term(information model)}} that provides semantic models for {{termplural(Asset)}}.*/
            private ref occurrence __unnamed12 [0..*] : 'Protocol Terms'::'MTConnectAssets Response Document';
        }
        occurrence def 'MTConnect Information Model' :> 'information model' {
            doc /* {{term(information model)}} that defines the semantics of the MTConnect Standard.*/
        }
        occurrence def 'Observation Information Model' :> 'MTConnect Information Model' {
            doc /* {{term(information model)}} that describes the {{term(streaming data)}} reported by a piece of equipment.*/
            private ref occurrence __unnamed9 [0..*] : 'Protocol Terms'::'MTConnectStreams Response Document';
        }
        occurrence def 'Device Information Model' :> 'MTConnect Information Model' {
            doc /* {{term(information model)}} that describes the physical and logical configuration for a piece of equipment and the data that may be reported by that equipment. */
            private ref occurrence __unnamed10 [0..*] : 'Protocol Terms'::'MTConnectDevices Response Document';
        }
        connection def 'has XML representation3' {
            end : 'Protocol Terms'::'MTConnectStreams Response Document' => target.Glossary::'Information Model Terms'::'Observation Information Model'::__unnamed9;
            private end : 'Observation Information Model';
        }
        connection def 'has XML representation1' {
            end : 'Protocol Terms'::'MTConnectDevices Response Document' => target.Glossary::'Information Model Terms'::'Device Information Model'::__unnamed10;
            private end : 'Device Information Model';
        }
        connection def 'has XML representation2' {
            end : 'Protocol Terms'::'MTConnectErrors Response Document' => target.Glossary::'Information Model Terms'::'Error Information Model'::__unnamed11;
            private end : 'Error Information Model';
        }
        connection def 'has XML representation' {
            end : 'Protocol Terms'::'MTConnectAssets Response Document' => target.Glossary::'Information Model Terms'::'Asset Information Model'::__unnamed12;
            private end : 'Asset Information Model';
        }
        occurrence def 'ExceptionReport Information Model' :> 'MTConnect Information Model' {
            doc /* {{term(information model)}} that describes the {{term(response document)}} returned by an {{term(agent)}} when it encounters an exception in the {{term(MTConnectAssets Response Document)}}, {{term(MTConnectDevices Response Document)}} or {{term(MTConnectStreams Response Document)}}.*/
            private ref occurrence [0..*] : 'Protocol Terms'::'MTConnectAssets Response Document';
        }
    }
    package 'Protocol Terms' {
        occurrence def 'MTConnectStreams Response Document' :> 'MTConnect Response Document' {
            doc /* {{term(response document)}} published by an {{term(MTConnect Agent)}} in response to a {{term(current request)}} or a {{term(sample request)}}.*/
        }
        occurrence def 'MTConnectAssets Response Document' :> 'MTConnect Response Document' {
            doc /* {{term(response document)}} published by an {{term(MTConnect Agent)}} in response to an {{term(asset request)}}.*/
        }
        occurrence def 'MTConnectDevices Response Document' :> 'MTConnect Response Document' {
            doc /* {{term(response document)}} published by an {{term(MTConnect Agent)}} in response to a {{term(probe request)}}.*/
        }
        occurrence def 'MTConnectErrors Response Document' :> 'MTConnect Response Document' {
            doc /* {{term(response document)}} published by an {{term(MTConnect Agent)}} whenever it encounters an error while interpreting an {{term(MTConnect Request)}}.*/
        }
        occurrence def 'MTConnect Response Document' {
            doc /* {{term(response document)}} published by an {{term(MTConnect Agent)}}.*/
        }
        occurrence def 'transport protocol' :> protocol {
            doc /* set of capabilities that provide the rules and procedures used to transport information between an {{term(agent)}} and a client software application through a {{term(physical connection)}}.*/
        }
        occurrence def 'sample request' :> 'MTConnect Request' {
            doc /* {{term(request)}} to an {{term(agent)}} to produce an {{term(MTConnectStreams Response Document)}} containing the {{term(Observation Information Model)}} for a set of timestamped {{termplural(observation)}} made by {{termplural(Component)}}.*/
        }
        occurrence def 'MTConnect Request' :> request {
            doc /* {{term(request)}} for information issued from a {{term(client)}} to an {{term(MTConnect Agent)}}.*/
        }
        occurrence def 'probe request' :> 'MTConnect Request' {
            doc /* {{term(request)}} to an {{term(agent)}} to produce an {{term(MTConnectDevices Response Document)}} containing the {{term(Device Information Model)}}.*/
        }
        occurrence def 'streaming data' :> 'publish and subscribe' {
            doc /* {{termplural(observation)}} published by a piece of equipment defined by the {{term(equipment metadata)}}.*/
        }
        occurrence def publish :> 'publish and subscribe' {
            doc /* sending of messages in a {{term(publish and subscribe)}} pattern.*/
        }
        occurrence def 'current request' :> 'MTConnect Request' {
            doc /* {{term(request)}} to an {{term(agent)}} to produce an {{term(MTConnectStreams Response Document)}} containing the {{term(Observation Information Model)}} for a snapshot of the latest {{termplural(observation)}} at the moment of the {{term(request)}} or at a given {{term(sequence number)}}.*/
        }
        occurrence def protocol {
            doc /* set of rules that allow two or more entities to transmit information from one to the other.*/
        }
        occurrence def 'data streaming' :> 'streaming data' {
            doc /* method for an {{term(agent)}} to provide a continuous stream of information in response to a single {{term(request)}} from a {{term(client)}}.*/
        }
        occurrence def 'publish and subscribe' :> protocol {
            doc 
            /* asynchronous communication method in which messages are exchanged between applications without knowing the identity of the sender or recipient.
             *
             * > Note: In the MTConnect Standard, a communications messaging pattern that may be used to publish {{term(streaming data)}} from an {{term(agent)}}. 
             *
             */
        }
        occurrence def subscribe :> 'publish and subscribe' {
            doc /* receiving messages in a {{term(publish and subscribe)}} pattern.*/
        }
        occurrence def 'asset request' :> 'MTConnect Request' {
            doc /* {{term(HTTP Request)}} to the {{term(agent)}} regarding {{termplural(Asset)}}.*/
        }
        occurrence def request :> protocol {
            doc /* communications method where a {{term(client)}} transmits a message to an {{term(agent)}}.  That message instructs the {{term(agent)}} to respond with specific information.*/
        }
        occurrence def response :> protocol {
            doc /* response {{term(interface)}} which responds to a {{term(request)}}.*/
        }
        occurrence def 'request and response' :> protocol {
            doc /* communications pattern that supports the transfer of information between an {{term(agent)}} and a {{term(client)}}. */
        }
        occurrence def 'MTConnectExceptionsReport Response Document' :> 'MTConnect Response Document' {
            doc /* {{term(response document)}} returned by an {{term(agent)}} when it encounters an exception in the {{term(MTConnectAssets Response Document)}}, {{term(MTConnectDevices Response Document)}} or {{term(MTConnectStreams Response Document)}}.*/
        }
    }
    occurrence def probe {
        doc /* instrument commonly used for measuring the physical geometrical characteristics of an object.*/
    }
    occurrence def heartbeat {
        doc /* function that indicates to a {{term(client)}} that the communications connection to an {{term(agent)}} is still viable during times when there is no new data available to report  often referred to as a "keep alive" message.*/
    }
    occurrence def element {
        doc /* constituent part or a basic unit of identifiable and definable data.*/
        private occurrence __unnamed13 [0..*] : 'XML Terms'::'attribute';
    }
    occurrence def 'higher level' :> 'XML Terms'::'parent element' {
        doc /* nested element that is above a lower level element.*/
    }
    occurrence def 'lower level' :> 'XML Terms'::'child element' {
        doc /* nested element that is below a higher level element.*/
    }
    connection def 'has attributes' {
        end : 'XML Terms'::'attribute' => target.Glossary::element::__unnamed13;
        private end : element;
    }
    occurrence def profile {
        doc /* extends a reference metamodel (such as {{term(UML)}}) by allowing to adapt or customize the metamodel with constructs that are specific to a particular domain, platform, or a software development method. */
    }
    occurrence def stereotype {
        doc /* defines how an existing {{term(UML)}} metaclass may be extended as part of a {{term(profile)}}.*/
    }
    package 'Industrial Terms' {
        occurrence def asset :> Thing, resource {
            doc 
            /* item, thing or entity that has potential or actual value to an organization. {{cite(ISO 55000:2014)}}
             *
             * > Note 1 to entry: Value can be tangible or intangible, financial or non-financial, and includes consideration of risks and liabilities. It can be positive or negative at different stages of the asset life.
             *
             * > Note 2 to entry: Physical assets usually refer to equipment, inventory and properties owned by the organization. Physical assets are the opposite of intangible assets, which are non-physical assets such as leases, brands, digital assets, use rights, licences, intellectual property rights, reputation or agreements.
             *
             * > Note 3 to entry: A grouping of assets referred to as an asset system could also be considered as an asset.
             *
             */
        }
        occurrence def configuration :> Thing {
            doc /* information about an {{term(engineered system)}} describing its physical layout, functional characteristics, and relationships with other {{termplural(engineered system)}}*/
        }
        occurrence def 'engineered system' :> Thing, resource {
            doc /* logical or physical entity that may produce {{termplural(observation)}} about itself.*/
            private ref occurrence 'part of' [0..1] : 'engineered system';
            private ref occurrence 'has part' [0..*] : 'engineered system';
            private ref occurrence 'makes observation' [0..*] : observation;
            private ref occurrence observes [0..*] : observable;
            private ref occurrence 'made observation' [0..*] : 'MTConnect Terms'::Observation;
        }
        connection def {
            end 'part of' : 'engineered system' => 'has part'.Glossary::'Industrial Terms'::'engineered system'::'part of';
            end 'has part' : 'engineered system' => 'part of'.Glossary::'Industrial Terms'::'engineered system'::'has part';
        }
        dependency from 'engineered system' to observation;
        occurrence def observation {
            doc /* observed value of a property at a point in time.*/
            private ref occurrence 'made by' [1] : 'engineered system';
            private ref occurrence 'made for' [1] : observable;
        }
        occurrence def observable {
            doc /* quality, property, or characteristic that can be observed.*/
            private ref occurrence 'observed by' [1] : 'engineered system';
            private ref occurrence 'has observation' [0..*] : observation;
        }
        occurrence def observe {
            doc /* act of measuring or determining the value of a property at a point in time.*/
        }
        dependency from observation to asset;
        occurrence def 'engineering units' {
            doc /* quantity, dimension, or magnitude used in engineering adopted as a standard in terms of which the magnitude of other quantities of the same kind can be expressed or calculated.*/
        }
        occurrence def 'equipment metadata' {
            doc /* {{term(metadata)}} that defines both the entities that represent the physical and logical parts and sub-parts of each piece of equipment, the relationships between those parts and sub-parts, and the definitions of the {{termplural(DataItem)}} associated with that piece of equipment.*/
        }
        occurrence def equipment {
            doc 
            /* represents anything that can publish information and is used in the operations of a manufacturing facility shop floor.  
             *
             * > Note: Examples include machine tools, ovens, sensor units, workstations, software applications, and bar feeders.
             *
             */
        }
        occurrence def 'raw material' {
            doc /* crude or processed material that can be converted by manufacture, processing, or combination into a new and useful product.*/
        }
        occurrence def sensor {
            doc /* {{term(sensing element)}} that responds to a physical stimulus and transmits a resulting signal.*/
        }
        occurrence def 'sensor configuration' {
            doc /* data in the {{term(MTConnectDevices Response Document)}} that provides the information required for maintenance and support of the {{term(sensor unit)}}.*/
        }
        occurrence def 'sensor data' {
            doc /* value of a physical quantity reported by a measuring instrument or controller as an {{term(observation)}}.*/
        }
        occurrence def 'sensor unit' {
            doc /* intelligent piece of equipment that manages the signals of one or more {{termplural(sensing element)}} and provides the measured values.*/
        }
        occurrence def 'sensor element' {
            doc /* provides a signal or measured value.*/
        }
        occurrence def 'physical connection' {
            doc /* network transmission technologies that physically interconnect an {{term(agent)}}.*/
        }
        occurrence def 'control limit' {
            doc /* limit used to indicate whether a process variable is stable and in control.*/
        }
        occurrence def condition {
            doc /* ability of a piece of equipment or {{term(Component)}} to function to specification.*/
        }
        occurrence def 'condition state' {
            doc /* indicator of the {{term(condition)}}.*/
        }
        private occurrence def Thing {
            doc 
            /* property holder.
             *
             * > Note 1 to entry: Property holders are used to define properties that have no specific owner, or “top level” properties. These properties are generally referenced by other properties. {{cite(https://www.omg.org/spec/NIEM-UML/1.0)}}
             *
             * > Note 2 to entry: Property holder is equivalent to one topmost class of which all other classes are subclasses.
             *
             * !MTConnect Terms.png!*/
        }
        connection def {
            end 'makes observation' : observation => 'made by'.Glossary::'Industrial Terms'::'engineered system'::'makes observation';
            end 'made by' : 'engineered system' => 'makes observation'.Glossary::'Industrial Terms'::observation::'made by';
        }
        connection def {
            end observes : observable => 'observed by'.Glossary::'Industrial Terms'::'engineered system'::observes;
            end 'observed by' : 'engineered system' => observes.Glossary::'Industrial Terms'::observable::'observed by';
        }
        occurrence def resource {
            doc /* physical or logical entity used by an organization*/
        }
        connection def {
            end 'made for' : observable => 'has observation'.Glossary::'Industrial Terms'::observation::'made for';
            end 'has observation' : observation => 'made for'.Glossary::'Industrial Terms'::observable::'has observation';
        }
    }
    occurrence def 'top level' {
        doc /* element that represents the most significant physical or logical functions of a piece of equipment.*/
    }
    occurrence def 'cartesian coordinate system' {
        doc /* 3D orthogonal coordinate system {{cite(ISO/IEC 19794-5:2011(en))}}.*/
    }
    occurrence def characteristic {
        doc /* control placed on an element of a {{term(feature)}} such as its size, location, or form, which may be a specification limit, a nominal with tolerance, or some other numerical or non-numerical control. {{cite(QIF 3.0 3.4.29)}}. {{cite(AS9102-B)}}.*/
    }
    occurrence def feature {
        doc /* topological entity(ies) or design requirements related to a geometric model. {{cite(QIF 3.0-3.4.59)}}*/
    }
    occurrence def location {
        doc /* place or named space associated with an object or that can be occupied by an object.*/
    }
    occurrence def position :> location {
        doc /* {{term(location)}} that is represented by a point in space relative to a reference.*/
    }
    occurrence def uncertainty {
        doc 
        /* uncertainty (of measurement) parameter, associated with the result of a measurement, that characterizes the dispersion of the values that could reasonably be attributed to the measurand. {{cite(JCGM 100:2008 2.2.3)}}
         *
         * > Note: Use of the term uncertainty refers to uncertainty of measurement.*/
    }
    occurrence def 'standard uncertainty' :> uncertainty {
        doc /* {{term(uncertainty)}} of the result of a measurement expressed as a standard deviation. {{cite(JCGM 100:2008 2.3.1)}}*/
    }
    occurrence def 'combined standard uncertainty' :> 'standard uncertainty' {
        doc /* {{term(standard uncertainty)}} of the result of a measurement when that result is obtained from the values of a number of other quantities, equal to the positive square root of a sum of terms, the terms being the variances or covariances of these other quantities weighted according to how the measurement result varies with changes in these quantities. {{cite(JCGM 100:2008 2.3.4)}}*/
    }
    occurrence def 'condition activation' {
        doc /* state transition from `Normal` to either `Warning` or `Fault`.*/
    }
}
package 'Reference Agent Architecture' {
    occurrence def Agent {
        private occurrence __unnamed15 [1..*] : 'Reference Agent Architecture'::Source;
        private occurrence __unnamed17 [1..*] : 'Reference Agent Architecture'::Sink;
        private occurrence __unnamed19 [1] : AssetStroage;
        private ref occurrence __unnamed20 : Pipeline;
    }
    package Rest {
        package Storage {
            occurrence def CircularBufffer;
        }
    }
    package Source {
        occurrence def MQTTDataSource :> 'Reference Agent Architecture'::Source;
        occurrence def AdapterDataSource :> 'Reference Agent Architecture'::Source;
        flow ;
    }
    package Sink {
        occurrence def RestSink :> 'Reference Agent Architecture'::Sink {
            private occurrence __unnamed14 [1] : Rest::Storage::CircularBufffer;
        }
        flow ;
        connection def {
            end : Rest::Storage::CircularBufffer => target.'Reference Agent Architecture'::Sink::RestSink::__unnamed14;
            private end : RestSink;
        }
    }
    package Transformation {
        flow ;
    }
    package Printer {
        occurrence def XmlPrinter;
        occurrence def JsonPrinter;
    }
    package Parser {
        occurrence def XmlParser;
        occurrence def JsonParser;
    }
    package InformationModel {
        occurrence def Observation {
            private ref occurrence hasValue : ObservationValue;
        }
        occurrence def Sample :> Observation {
            private ref occurrence hasValue :>> 'Reference Agent Architecture'::InformationModel::Observation::hasValue : NumericValue;
        }
        occurrence def Event :> Observation {
            private ref occurrence hasValue :>> 'Reference Agent Architecture'::InformationModel::Observation::hasValue : TextValue;
        }
        occurrence def Contition :> Observation {
            private ref occurrence hasValue :>> 'Reference Agent Architecture'::InformationModel::Observation::hasValue : ConditionValue;
        }
        occurrence def DataSet;
        occurrence def ObservationValue;
        occurrence def TextValue :> ObservationValue;
        occurrence def NumericValue :> TextValue;
        occurrence def ControlledVocabularyValue :> TextValue;
        occurrence def ConditionValue :> ObservationValue;
        occurrence def Table :> DataSet;
        occurrence def TimeSeries;
        occurrence def Component {
            private occurrence : DataItem;
            private occurrence : Configuration;
            private occurrence : Reference;
        }
        occurrence def DataItem;
        occurrence def Device :> Component;
        occurrence def Configuration;
        occurrence def Reference;
    }
    abstract occurrence def Service {
        private services;
        private attribute name : Profile::DataTypes::string;
    }
    occurrence def RestSink;
    occurrence def DataSinkService :> Service;
    occurrence def MQTTSink;
    occurrence def DataSourceService :> Service;
    occurrence def RestService :> Service;
    occurrence def TransformationService :> Service;
    occurrence def StorageService :> Service;
    occurrence def RestSource;
    occurrence def MQTTSource;
    abstract occurrence def Source {
        private occurrence __unnamed16 [1] : Pipeline;
    }
    connection def {
        end : 'Reference Agent Architecture'::Source => target.'Reference Agent Architecture'::Agent::__unnamed15;
        private end : Agent;
    }
    abstract occurrence def Pipeline {
        private occurrence __unnamed18 : Transformtion;
        private ref occurrence __unnamed21 : Agent;
    }
    connection def run {
        end : Pipeline => target.'Reference Agent Architecture'::Source::__unnamed16;
        private end : 'Reference Agent Architecture'::Source;
    }
    abstract occurrence def Sink;
    connection def publish {
        end : 'Reference Agent Architecture'::Sink => target.'Reference Agent Architecture'::Agent::__unnamed17;
        private end : Agent;
    }
    abstract occurrence def Transformtion {
        private occurrence __unnamed22 [0..*] : Transformtion;
    }
    connection def {
        end : Transformtion => target.'Reference Agent Architecture'::Pipeline::__unnamed18;
        private end [1..*] ref : Pipeline;
    }
    occurrence def AssetStroage;
    connection def {
        end : AssetStroage => target.'Reference Agent Architecture'::Agent::__unnamed19;
        private end : Agent;
    }
    connection def delivers {
        end : Pipeline => target.'Reference Agent Architecture'::Agent::__unnamed20;
        end : Agent => source.'Reference Agent Architecture'::Pipeline::__unnamed21;
    }
    connection def next {
        end : Transformtion => target.'Reference Agent Architecture'::Transformtion::__unnamed22;
        private end : Transformtion;
    }
    occurrence def 'OPC UA Sink' :> 'Reference Agent Architecture'::Sink;
    occurrence def 'NC Link' :> 'Reference Agent Architecture'::Sink;
    occurrence def 'MQTT Sink' :> 'Reference Agent Architecture'::Sink;
    package Pipelines {
        action def 'Shdr Pipeline' {
            first startShot then Start;
            first DeliverConnectionStatus then __unnamed23;
            first DeliverCommand then __unnamed23;
            flow yes from 'ignore timestamps?'.__unnamed24 to IgnoreTimestamp.input;
            first DeliverAsset then __unnamed23;
            first DeliverAssetCommand then __unnamed23;
            flow from 'Upcase Data Item Value?'.__unnamed25 to __unnamed26.__unnamed27;
            flow from DuplicateFilter.observation to 'duplicate?'.__unnamed28;
            flow yes from 'Upcase Data Item Value?'.__unnamed25 to UpcaseValue.input;
            flow from __unnamed26.__unnamed29 to DuplicateFilter.input;
            flow no from 'ignore timestamps?'.__unnamed24 to ExtractTimestamps.input;
            flow from DeltaFilter.output to 'suppressed?'.__unnamed30;
            flow from PeriodFilter.output to 'Shdr Pipeline'::'suppressed?'.__unnamed31;
            flow yes from 'Conversion Required?'.__unnamed32 to ConvertSample.input;
            flow no from 'Conversion Required?'.__unnamed32 to __unnamed33.__unnamed34;
            first DeliverObservation then __unnamed23;
            flow from __unnamed33.__unnamed35 to DeliverObservation.observation;
            action Start {
                out Data : 'Entity{Data}';
                out ConnectionStatus : 'Entity{ConnectionStatus}';
                out Command : 'Entity{Command}';
            }
            action DeliverConnectionStatus { in input : 'Entity{ConnectionStatus}'; }
            action DeliverCommand { in input : 'Entity{Command}'; }
            action __unnamed23 terminate;
            action ShdrTokenizer {
                in input : 'Entity{Data}';
                out output;
            }
            decide 'ignore timestamps?' {
                out __unnamed24;
            }
            action IgnoreTimestamp {
                in input : Tokens;
                out output;
            }
            action ExtractTimestamps {
                in input : Tokens;
                out output : Timestamped;
            }
            action ShdrTokenMapper {
                in input : Timestamped;
                out output;
                out observation;
                out asset;
                out assetCommand;
            }
            action DeliverAsset { in input : 'Asset Information Model'::Asset; }
            action DeliverAssetCommand { in input : AssetCommand; }
            decide 'Upcase Data Item Value?' {
                out __unnamed25;
            }
            action UpcaseValue {
                in input : 'Observation Information Model'::Observation;
                out output;
            }
            action DuplicateFilter {
                in input : 'Observation Information Model'::Observation;
                out observation;
            }
            decide 'duplicate?' {
                in __unnamed28;
            }
            merge __unnamed26 {
                in __unnamed27;
                out __unnamed29;
            }
            action DeltaFilter {
                in input : 'Observation Information Model'::Observation;
                out output;
            }
            decide 'suppressed?' {
                in __unnamed30;
            }
            action PeriodFilter {
                in input : 'Observation Information Model'::Observation;
                out output;
            }
            decide 'suppressed?' {
                in __unnamed31;
            }
            decide 'Conversion Required?' {
                out __unnamed32;
            }
            action ConvertSample {
                in input;
                out output;
            }
            action DeliverObservation { in observation; }
            decide __unnamed33 {
                in __unnamed34;
                out __unnamed35;
            }
        }
        part def 'Entity{Command}' :> Entity {
            attribute name :>> name : Profile::DataTypes::string default "Command";
            attribute source : Profile::DataTypes::string;
        }
        part def 'Entity{Message}' :> Entity {
            attribute name :>> name : Profile::DataTypes::string default "\"Message\"";
            attribute sorce : Profile::DataTypes::string;
            attribute topic : Profile::DataTypes::string;
        }
        part def 'Entity{Data}' :> Entity {
            attribute name :>> name : Profile::DataTypes::string default "Data";
            attribute source : Profile::DataTypes::string;
        }
        part def Entity {
            attribute name : Profile::DataTypes::string;
            attribute value : Profile::DataTypes::string;
        }
        part def 'Entity{ConnectionStatus}' :> Entity {
            private attribute name :>> name : Profile::DataTypes::string default "ConnectionStatus";
            attribute source : Profile::DataTypes::string;
        }
        part def Tokens :> Entity {
            attribute name : Profile::DataTypes::string;
            attribute source : Profile::DataTypes::string;
            attribute tokens [0..*] : Profile::DataTypes::string;
        }
        part def Timestamped :> Tokens {
            attribute timestamp : Profile::DataTypes::datetime;
        }
        attribute def date;
        part def Observations :> Timestamped {
            ref part value [0..*] : 'Observation Information Model'::Observation;
        }
        attribute def Entity;
        connection def {
            end value : 'Observation Information Model'::Observation => target.value;
            private end : Observations;
        }
        part def AssetCommand :> Timestamped {
            attribute name :>> 'Entity{Command}'::name : Profile::DataTypes::string default "AssetCommand";
            attribute source : Profile::DataTypes::string;
            attribute assetId [0..1] : Profile::DataTypes::string;
            attribute type [0..1] : Profile::DataTypes::string;
            attribute device [0..1] : Profile::DataTypes::string;
        }
        action def 'MQTT Pipeline' {
            first startShot then Start;
            first DeliverConnectionStatus then __unnamed36;
            first DeliverCommand then __unnamed36;
            flow yes from 'ignore timestamps?'.__unnamed37 to IgnoreTimestamp.input;
            first DeliverAsset then __unnamed36;
            first DeliverAssetCommand then __unnamed36;
            flow from 'Upcase Data Item Value?'.__unnamed38 to __unnamed39.__unnamed40;
            flow from DuplicateFilter.observation to 'duplicate?'.__unnamed41;
            flow yes from 'Upcase Data Item Value?'.__unnamed38 to UpcaseValue.input;
            flow from __unnamed39.__unnamed42 to DuplicateFilter.input;
            flow no from 'ignore timestamps?'.__unnamed37 to ExtractTimestamps.input;
            flow from DeltaFilter.output to 'suppressed?'.__unnamed43;
            flow from PeriodFilter.output to 'MQTT Pipeline'::'suppressed?'.__unnamed44;
            flow yes from 'Conversion Required?'.__unnamed45 to ConvertSample.input;
            flow no from 'Conversion Required?'.__unnamed45 to __unnamed46.__unnamed47;
            first DeliverObservation then __unnamed36;
            flow from __unnamed46.__unnamed48 to DeliverObservation.observation;
            action Start {
                out Data : 'Entity{Data}';
                out ConnectionStatus : 'Entity{ConnectionStatus}';
                out Command : 'Entity{Command}';
                out output;
            }
            action DeliverConnectionStatus { in input : 'Entity{ConnectionStatus}'; }
            action DeliverCommand { in input : 'Entity{Command}'; }
            action __unnamed36 terminate;
            action ShdrTokenizer {
                in input : 'Entity{Data}';
                in input1 : DataMessage;
                out output;
            }
            decide 'ignore timestamps?' {
                out __unnamed37;
            }
            action IgnoreTimestamp {
                in input : Tokens;
                out output;
            }
            action ExtractTimestamps {
                in input : Tokens;
                out output : Timestamped;
            }
            action ShdrTokenMapper {
                in input : Timestamped;
                out output;
                out observation;
                out asset;
                out assetCommand;
            }
            action DeliverAsset { in input : 'Asset Information Model'::Asset; }
            action DeliverAssetCommand { in input : AssetCommand; }
            decide 'Upcase Data Item Value?' {
                out __unnamed38;
            }
            action UpcaseValue {
                in input : 'Observation Information Model'::Observation;
                out output;
            }
            action DuplicateFilter {
                in input : 'Observation Information Model'::Observation;
                out observation;
            }
            decide 'duplicate?' {
                in __unnamed41;
            }
            merge __unnamed39 {
                in __unnamed40;
                out __unnamed42;
            }
            action DeltaFilter {
                in input : 'Observation Information Model'::Observation;
                out output;
            }
            decide 'suppressed?' {
                in __unnamed43;
            }
            action PeriodFilter {
                in input : 'Observation Information Model'::Observation;
                out output;
            }
            decide 'suppressed?' {
                in __unnamed44;
            }
            decide 'Conversion Required?' {
                out __unnamed45;
            }
            action ConvertSample {
                in input;
                out output;
            }
            action DeliverObservation { in observation; }
            decide __unnamed46 {
                in __unnamed47;
                out __unnamed48;
            }
            action TopicMapper {
                in input : 'Entity{M';
                out output;
                out output1;
            }
            action JsonMapper {
                in input : JsonMessage;
                out disabled : 'Observation Information Model'::Observation;
            }
        }
        part def 'Entity{M';
        part def PipelineMessage :> Entity {
            ref part dataItem [0..1] : 'Device Information Model'::DataItems::DataItem;
            ref part device : 'Device Information Model'::Device;
            attribute name :>> name : Profile::DataTypes::string default "Message";
        }
        connection def {
            end dataItem : 'Device Information Model'::DataItems::DataItem => target.dataItem;
            private end : PipelineMessage;
        }
        connection def {
            end device : 'Device Information Model'::Device => target.device;
            private end [0..1] ref : PipelineMessage;
        }
        part def JsonMessage :> PipelineMessage;
        part def DataMessage :> PipelineMessage;
        part def Transform {
            part guard : Guard;
            part next [0..*] : Transform;
        }
        enum def GuardResult {
            CONTINUE;
            SKIP;
            RUN;
        }
        part def Guard;
        part def TypeGuard :> Guard {
            attribute type : T;
        }
        part def ExactTypeGuard :> Guard {
            attribute type : T;
        }
        part def EntityNameGuard :> Guard {
            attribute name : Profile::DataTypes::string;
        }
        attribute def T;
        part def LambdaGuard :> Guard {
            attribute lambda : F;
        }
        attribute def F;
        part def ConvertSample :> Transform;
        connection def {
            end next : Transform => target.next;
            private end : Transform;
        }
    }
}
package 'Development Process' {
    action def 'Development Process' {
        first startShot then 'New Issue (WG)';
        succession 'Consider for Next Release' first 'New Issue (WG)' then 'In Discussion (WG)';
        succession 'Completed Content' first 'In Discussion (WG)' then 'Reviewing (RB)';
        first 'Reviewing (RB)' then 'Review Complete ';
        succession 'Needs more work' first 'Review Complete ' then 'In Discussion (WG)';
        succession 'Content Accepted' first 'Review Complete ' then 'Models and Docs (DM)';
        first 'Models and Docs (DM)' then 'Final Review (WG)';
        first 'Final Review (WG)' then __unnamed49;
        succession 'documentation needs correction' first __unnamed49 then 'Models and Docs (DM)';
        succession 'content is correct' first __unnamed49 then 'EC Review (EC)';
        first 'EC Review (EC)' then __unnamed50;
        succession 'issues with content' first __unnamed50 then 'In Discussion (WG)';
        succession 'IP or Copyright Issues' first __unnamed51 then 'In Discussion (WG)';
        succession 'content is good' first __unnamed50 then '90 Day Review (SC)';
        first '90 Day Review (SC)' then __unnamed51;
        succession 'No issues' first __unnamed51 then 'Vote (SC)';
        first 'Vote (SC)' then __unnamed52;
        succession Released first __unnamed52 then Public;
        succession Rejected first __unnamed52 then 'EC Review (EC)';
        action Public terminate;
        action 'New Issue (WG)';
        action 'In Discussion (WG)';
        decide 'Review Complete ';
        action 'Reviewing (RB)';
        action 'Models and Docs (DM)';
        action 'Final Review (WG)';
        decide __unnamed49;
        action 'EC Review (EC)';
        decide __unnamed50;
        action '90 Day Review (SC)';
        action 'Vote (SC)';
        decide __unnamed51;
        decide __unnamed52;
    }
}
package 'Supporting Documents' {
    package 'Common Documents' {
        comment /* Acronyms*/
        comment /* MTConnect Class*/
        comment /* MTConnect Specification and Materials*/
        comment /* MTConnect References*/
        comment /* External References*/
        comment /* Main Template TEX*/
        comment /* Appendix*/
        comment /* Main Template MD*/
        doc 
        /*
         * {{newacronym{API}{API}{application programming interface}()}}
         * {{newacronym{BOM}{BOM}{bill of materials}()}}
         * {{newacronym{DER}{DER}{designated-engineering representative}()}}
         * {{newacronym{DMC}{DMC}{digital manufacturing certificate}()}}
         * {{newacronym{SME}{SME}{small-to-medium enterprise}()}}
         * {{newacronym{URI}{URI}{Uniform Resource Identifier}()}}
         * {{newacronym{URL}{URL}{Uniform Resource Locator}()}}
         * {{newacronym{URN}{URN}{Uniform Resource Name}()}}
         * {{newacronym{UTC}{UTC}{Coordinated Universal Time}()}}
         *
         *
         * {{newacronym{2D}{2D}{two-dimensional}()}}
         * {{newacronym{3D}{3D}{three-dimensional}()}}
         * {{newacronym{AI}{AI}{artificial intelligence}()}}
         * {{newacronym{ALM}{ALM}{application lifecycle management}()}}
         * {{newacronym{AMT}{AMT}{The Association for Manufacturing Technology}()}}
         * {{newacronym{ANSI}{ANSI}{American National Standards Institute}()}}
         * {{newacronym{AP}{AP}{Application Protocol}()}}
         * {{newacronym{ASME}{ASME}{American Society of Mechanical Engineers}()}}
         * {{newacronym{ASTM}{ASTM}{American Society for Testing and Materials}()}}
         * {{newacronym{AWS}{AWS}{American Welding Society}()}}
         * {{newacronym{BDD}{BDD}{block definition diagram}()}}
         * {{newacronym{BST}{BST}{Board on Standardization and Testing}()}}
         * {{newacronym{CA}{CA}{certificate authority}()}}
         * {{newacronym{CAD}{CAD}{computer-aided design}()}}
         * {{newacronym{CAE}{CAE}{computer-aided engineering}()}}
         * {{newacronym{CAI}{CAI}{computer-aided inspection}()}}
         * {{newacronym{CAM}{CAM}{computer-aided manufacturing}()}}
         * {{newacronym{CAx}{CAx}{computer-aided technologies}()}}
         * {{newacronym{CFD}{CFD}{computational fluid dynamics}()}}
         * {{newacronym{CM}{CM}{configuration management}()}}
         * {{newacronym{CMS}{CMS}{coordinate-measurement system}()}}
         * {{newacronym{CNRI}{CNRI}{Corporation for National Research Initiatives}()}}
         * {{newacronym{CPM}{CPM}{Core Product Model}()}}
         * {{newacronym{CPM2}{CPM2}{Revised Core Product Model}()}}
         * {{newacronym{CPSC}{CPSC}{Consumer Product Safety Commission}()}}
         * {{newacronym{C&R}{C\&R}{cause and remedy}()}}
         * {{newacronym{cUAV}{cUAV}{configurable unmanned aerial vehicle}()}}
         * {{newacronym{DARPA}{DARPA}{Defense Advanced Research Projects Agency}()}}
         * {{newacronym{DFM}{DFM}{design for manufacturing}()}}
         * {{newacronym{DLA}{DLA}{Defense Logistics Agency}()}}
         * {{newacronym{DMSC}{DMSC}{Dimensional Metrology Standards Consortium}()}}
         * {{newacronym{DNS}{DNS}{Domain Name System}()}}
         * {{newacronym{DoD}{DoD}{U.S. Department of Defense}()}}
         * {{newacronym{DOI}{DOI}{Distributed Object Identifier}()}}
         * {{newacronym{DRM}{DRM}{digital rights management}()}}
         * {{newacronym{ECR}{ECR}{engineering change request}()}}
         * {{newacronym{ERP}{ERP}{enterprise resource planning}()}}
         * {{newacronym{FAA}{FAA}{Federal Aviation Administration}()}}
         * {{newacronym{FAIR}{FAIR}{first article inspection reporting}()}}
         * {{newacronym{FDA}{FDA}{Food and Drug Administration}()}}
         * {{newacronym{FEA}{FEA}{finite-element analysis}()}}
         * {{newacronym{GD&T}{GD\&T}{geometric dimensions and tolerances}()}}
         * {{newacronym{GID}{GID}{global identifier}()}}
         * {{newacronym{HTML}{HTML}{Hypertext Markup Language}()}}
         * {{newacronym{HTTP}{HTTP}{Hypertext Transfer Protocol}()}}
         * {{newacronym{HTTPS}{HTTPS}{Hypertext Transfer Protocol over Secure Sockets Layer}()}}
         * {{newacronym{ID}{ID}{identifier}()}}
         * {{newacronym{IEEE}{IEEE}{Institute of Electrical and Electronics Engineers}()}}
         * {{newacronym{IIoT}{IIoT}{industrial internet of things}()}}
         * {{newacronym{INCOSE}{INCOSE}{International Council on Systems Engineering}()}}
         * {{newacronym{I/O}{I/O}{in-out}()}}
         * {{newacronym{IP}{IP}{intellectual property}()}}
         * {{newacronym{ISO}{ISO}{International Standards Organization}()}}
         * {{newacronym{ISS}{ISS}{International Space Station}()}}
         * {{newacronym{IT}{IT}{information technology}()}}
         * {{newacronym{ITU-T}{ITU-T}{Telecommunication Standardization Sector of the International Telecommunication Union}()}}
         * {{newacronym{JSON}{JSON}{JavaScript Object Notation}()}}
         * {{newacronym{JT}{JT}{Jupiter Tesselation}()}}
         * {{newacronym{LHS}{LHS}{Lifecycle Handler System}()}}
         * {{newacronym{LIFT}{LIFT}{Lifecycle Information Framework and Technology}()}}
         * {{newacronym{LOI}{LOI}{Lifecycle Object Identifier}()}}
         * {{newacronym{MAC}{MAC}{media access control}()}}
         * {{newacronym{MADE}{MADE}{Manufacturing Automation and Design Engineering}()}}
         * {{newacronym{MBD}{MBD}{model-based definition}()}}
         * {{newacronym{MBE}{MBE}{Model-Based Enterprise}()}}
         * {{newacronym{MBI}{MBI}{model-based inspection}()}}
         * {{newacronym{MBM}{MBM}{model-based manufacturing}()}}
         * {{newacronym{MBSD}{MBSD}{model-based standards development}()}}
         * {{newacronym{MBSE}{MBSE}{model-based systems engineering}()}}
         * {{newacronym{MEDALS}{MEDALS}{Military Engineering Data Asset Locator System}()}}
         * {{newacronym{MES}{MES}{manufacturing execution system}()}}
         * {{newacronym{MOI}{MOI}{manufacturing object identifier}()}}
         * {{newacronym{MTC}{MTC}{Manufacturing Technology Centre}()}}
         * {{newacronym{NASA}{NASA}{National Aeronautics and Space Administration}()}}
         * {{newacronym{NC}{NC}{numerical control}()}}
         * {{newacronym{NIST}{NIST}{National Institute of Standards and Technology}()}}
         * {{newacronym{NNMI}{NNMI}{National Network of Manufacturing Innovation}()}}
         * {{newacronym{NSF}{NSF}{National Science Foundation}()}}
         * {{newacronym{NTSC}{NTSC}{National Transportation Safety Board}()}}
         * {{newacronym{OASIS}{OASIS}{Organization for the Advancement of Structured Information Standards}()}}
         * {{newacronym{ODI}{ODI}{Open Data Institute}()}}
         * {{newacronym{OEM}{OEM}{original equipment manufacturer}()}}
         * {{newacronym{OOI}{OOI}{Ocean Observatories Initiative}()}}
         * {{newacronym{OSLC}{OSLC}{Open Services for Lifecycle Collaboration}()}}
         * {{newacronym{OSTP}{OSTP}{Office of Science and Technology Policy}()}}
         * {{newacronym{OT}{OT}{operational technology}()}}
         * {{newacronym{OWL}{OWL}{Ontology Web Language}()}}
         * {{newacronym{PDF}{PDF}{Portable Document Format}()}}
         * {{newacronym{PDM}{PDM}{product-data management}()}}
         * {{newacronym{PDQ}{PDQ}{product-data quality}()}}
         * {{newacronym{PHM}{PHM}{prognosis and health monitoring}()}}
         * {{newacronym{PI}{PI}{principal investigator}()}}
         * {{newacronym{PLCS}{PLCS}{Product Life Cycle Support}()}}
         * {{newacronym{PLM}{PLM}{product lifecycle management}()}}
         * {{newacronym{PLOT}{PLOT}{product lifecycle of trust}()}}
         * {{newacronym{PMI}{PMI}{product and manufacturing information}()}}
         * {{newacronym{PRC}{PRC}{Product Representation Compact}()}}
         * {{newacronym{PSI}{PSI}{Physical Science Informatics}()}}
         * {{newacronym{PTAB}{PTAB}{Primary Trustworthy Digital Repository Authorization Body Ltd.}()}}
         * {{newacronym{QIF}{QIF}{Quality Information Framework}()}}
         * {{newacronym{QMS}{QMS}{quality management system}()}}
         * {{newacronym{RDF}{RDF}{Resource Description Framework}()}}
         * {{newacronym{REST}{REST}{Representational State Transfer}()}}
         * {{newacronym{RII}{RII}{receiving and incoming inspection}()}}
         * {{newacronym{SaaS}{SaaS}{software-as-a-service}()}}
         * {{newacronym{SAML}{SAML}{Security Assertion Markup Language}()}}
         * {{newacronym{SC}{SC}{Standards Committee}()}}
         * {{newacronym{SDO}{SDO}{Standards Development Organization}()}}
         * {{newacronym{SFTP}{SFTP}{Secure File Transfer Protocol}()}}
         * {{newacronym{SKOS}{SKOS}{Simple Knowledge Organization System}()}}
         * {{newacronym{SLH}{SLH}{system lifecycle handler}()}}
         * {{newacronym{SLR}{SLR}{systematic literature review}()}}
         * {{newacronym{S/MIME}{S/MIME}{Secure/Multipurpose Internet Mail Extensions}()}}
         * {{newacronym{SMOPAC}{SMOPAC}{Smart Manufacturing Operations Planning and Control}()}}
         * {{newacronym{sms}{SMS Test Bed}{Smart Manufacturing Systems Test Bed}()}}
         * {{newacronym{SOA}{SOA}{service-oriented architecture}()}}
         * {{newacronym{SPMM}{SPMM}{semantic-based product metamodel}()}}
         * {{newacronym{SSL}{SSL}{Secure Sockets Layer}()}}
         * {{newacronym{STEP}{STEP}{Standard for the Exchange of Product Model Data}()}}
         * {{newacronym{STEP AP242}{STEP AP242}{Standard for the Exchange of Product Model Data Application Protocol 242}()}}
         * {{newacronym{STL}{STL}{Stereolithography}()}}
         * {{newacronym{SysML}{SysML}{Systems Modeling Language}()}}
         * {{newacronym{TDP}{TDP}{technical data package}()}}
         * {{newacronym{TLS}{TLS}{Transport Layer Security}()}}
         * {{newacronym{TSM}{TSM}{Total System Model}()}}
         * {{newacronym{UML}{UML}{Unified Modeling Language}()}}
         * {{newacronym{UUID}{UUID}{Universally Unique Identifier}()}}
         * {{newacronym{V&V}{V\&V}{verification and validation}()}}
         * {{newacronym{W3C}{W3C}{World Wide Web Consortium}()}}
         * {{newacronym{WSN}{WSN}{Wirth Syntax Notation}()}}
         * {{newacronym{WWW}{WWW}{World Wide Web}()}}
         * {{newacronym{XML}{XML}{Extensible Markup Language}()}}
         * {{newacronym{X.509-PKI}{X.509-PKI}{Public Key Infrastructure}()}}
         * {{newacronym{X.509-PMI}{X.509-PMI}{Privilege Management Infrastructure}()}}
         * {{newacronym{XSD}{XSD}{XML Schema Definitions}()}}
         *
         * {{newacronym{OPC}{OPC}{OLE for Process Control}()}}
         * {{newacronym{UA}{UA}{Unified Architecture}()}}
         * {{newacronym{UAL}{UAL}{Unified Architecture Language}()}}
         * {{newacronym{HMI}{HMI}{Human Machine Interface}()}}
         * {{newacronym{PLC}{PLC}{Programmable Logic Controller}()}}
         * {{newacronym{SCADA}{SCADA}{Supervisory Control And Data Acquisition}()}}
         * {{newacronym{TCP/IP}{TCP/IP}{Transmission Control Protocol/Internet Protocol}()}}
         * {{newacronym{CNC}{CNC}{Computer Numerical Controller}()}}
         *
         *
         * {{newacronym{MOM}{MOM}{Message Orienged Middleware}()}}
         * {{newacronym{PMS}{PMS}{Production Management System}()}}
         * {{newacronym{ISV}{ISV}{Independent Software Vendor}()}}
         * {{newacronym{MQTT}{MQTT}{Message Queuing Telemetry Transport}()}}
         * {{newacronym{CDATA}{CDATA}{Character Data}()}}
         * {{newacronym{NMTOKEN}{NMTOKEN}{Name Token}()}}
         * {{newacronym{QName}{QName}{Qualified Name}()}}
         * {{newacronym{XPath}{XPath}{XML Path Language}()}}
         */
        doc 
        /* %   MTConnect Document Class    %
         *
         * \NeedsTeXFormat{LaTeX2e}
         * \ProvidesClass{mtconnect}[2018/02/13 LaTeX document class for MTConnect]
         *
         * %   Preliminary Declarations    %
         *
         * \LoadClass[12pt,letterpaper,twoside]{article}
         * \usepackage[utf8]{inputenc}
         * \usepackage[letterpaper,top=1.25in,%
         *             bottom=1.25in,footskip=0.5in]{geometry}
         *
         * \usepackage[citations,hybrid,smartEllipses,hashEnumerators,html,%
         *            pipeTables,tableCaptions,fencedCode,codeSpans,tightLists=false,%
         *            cacheDir=markdowncache]{markdown}%
         * \usepackage[absolute]{textpos}
         * \RequirePackage[htt]{hyphenat}				% Allow hyphenation of fixed space fonts
         * \RequirePackage{fancyvrb}
         * \RequirePackage{placeins}
         * \RequirePackage{booktabs}
         * \usepackage{morewrites}
         * \RequirePackage{times}					% Loads Adobe Times Roman Font (clone of Times New Roman)
         * \RequirePackage{mathptmx}				% Loads Adobe Times Roman Math Font
         * \RequirePackage{ifpdf}					% Enables switch between latex and pdflatex
         * \RequirePackage{stringstrings}			% Loads stringstrings to create Camel and Pascal case fonts
         * \RequirePackage{ifthen}					% Loads ifthen package for conditional statements
         * \RequirePackage[T1]{fontenc}			% Loads fontenc package for controlled vocabulary formatting
         * \let\BreakableUnderscore\undefined
         * \RequirePackage{graphicx}				% Loads graphicx package to include figures and images
         * \RequirePackage{fancyhdr}				% Loads fancyhdr package to modify headers and footers
         * %\RequirePackage[hyphens]{url}					% Loads url package to typeset URLs
         * \RequirePackage{lineno}					% Loads lineno package to apply line numbers to document
         * \RequirePackage{etoolbox}				% Loads etoolbox package to patch lineno package and suppress line numbers in section headings
         * \RequirePackage{sectsty}				% Loads sectsty package to modify font of section headings
         * \RequirePackage{xcolor}					% Loads xcolor package to define color for fonts and tables
         * \RequirePackage{colortbl}				% Loads colortbl package to provide colors for table shading
         * \RequirePackage{caption}				% Loads caption package to adjust caption font
         * \usepackage{listings}				% Loads listings package to typeset code samples
         * \lstset{ %default
         *     basicstyle=\footnotesize\fontfamily{pcr}\selectfont,
         *     numbers=left,
         *     stepnumber=1,
         *     xleftmargin=0.25in,
         * 	breaklines=true
         * }
         * \renewcommand\lstlistingname{Example}
         * \RequirePackage{hyperref}				% Loads hyperref package to link TOC/LOF/LOT
         * \RequirePackage{tocloft}				% Loads tocloft package to format TOC/LOF/LOT
         * \RequirePackage[ampersand]{easylist}	% Loads easylist package to simplify lists using &
         * \RequirePackage[english]{babel}
         * \RequirePackage{csquotes}
         * \RequirePackage{xstring}
         * \RequirePackage{siunitx}
         * \RequirePackage{upgreek}
         * \RequirePackage{longtable}
         * \RequirePackage{enumitem}
         * \usepackage{tabularray}
         * \usepackage{amsmath}
         * \usepackage{amssymb}
         * \usepackage[normalem]{ulem} %For deprecated items
         * \RequirePackage[acronym,toc,numberedsection,%
         *   abbreviations,automake,nonumberlist,%
         *   section=subsection]{glossaries-extra}
         * \usepackage{mdframed}
         * \usepackage{nameref}
         * \usepackage[titletoc,title]{appendix}
         * \usepackage{hanging}
         * \usepackage{titlesec}
         * \usepackage{xargs}
         * \newcommand{\sectionbreak}{\clearpage}
         *
         * \usepackage[backend=biber,style=alphabetic,]{biblatex}
         * \defbibheading{bibliography}[\bibname]{%
         *   \subsection{#1}}
         *
         * \usepackage{titlesec}
         *
         * %   Watermark   %
         *
         * %\usepackage{background}
         * %\backgroundsetup{contents=DRAFT, opacity=0.3, color=cyan, scale=9}
         *
         * % Formatting for MTConnect with registration mark, which is required in title and footer. 
         * \newcommand{\mtconnectregistered}{MTConnect\textsuperscript{\textregistered} }
         * % Formatting for MTConnect without registration mark, which can be used everywhere except title page(s) and footer. 
         * %\newcommand{\mtconnect}{MTConnect } %Use MTConnect
         *
         * \newcommand{\storedstringPCR}[1]{{\fontfamily{pcr}\selectfont #1}}
         *
         * %    Page Layout    %
         *
         * \setlength\paperheight{11in}
         * \setlength\paperwidth{8.5in}
         * \setlength\oddsidemargin{0.25in}
         * \setlength\evensidemargin{0.25in}
         *
         * \setlength\parindent{0pt}
         * \setlength\parskip{1em}
         *
         * %   Title Page  %
         *
         * \newcommand\@docnum{}
         * \newcommand\@doctitle{}
         * \newcommand\@versionnum{}
         * \newcommand\@preparedfor{}
         * \newcommand\@preparedby{}
         * \newcommand\@preparedon{}
         * \newcommand\@preparedfrom{}
         * \newcommand{\docnum}[1]{\gdef\@docnum{#1}}
         * \newcommand{\doctitle}[1]{\gdef\@doctitle{#1}}
         * \newcommand{\versionnum}[1]{\gdef\@versionnum{#1}}
         * \newcommand{\preparedfor}[1]{\gdef\@preparedfor{#1}}
         * \newcommand{\preparedby}[1]{\gdef\@preparedby{#1}}
         * \newcommand{\preparedon}[1]{\gdef\@preparedon{#1}}
         * \newcommand{\preparedfrom}[1]{\gdef\@preparedfrom{#1}}
         *
         * \renewcommand{\maketitle}{%
         * 	\begin{titlepage}%
         *     	\begin{flushleft}%
         *         	\includegraphics[width=0.5\linewidth]{mtconnect.png} \\%
         *         \end{flushleft}%
         *         \vfill%
         *         \begin{center}%
         *         	\Huge{\textbf{\mtconnectregistered Standard}} \\%
         *             \huge{\@docnum\ -- \@doctitle} \\%
         *             \LARGE{Version \@versionnum} \\%
         *         \end{center}%
         *         \vfill%
         *         \hspace*{\fill}%
         * 		\begin{tabular}[t]{l@{}}%
         * 			Prepared for: \@preparedfor \\%
         * 			Prepared from: \@preparedfrom \\%
         *         	Prepared on: \@preparedon \\%
         * 		\end{tabular}%
         * 		\vfill%
         * 		\noindent \footnotesize{\mtconnectregistered is a registered trademark of AMT - The Association for Manufacturing Technology. Use of MTConnect is limited to use as specified on \url{http://www.mtconnect.org/}.}%
         *     \end{titlepage}%
         *     \setcounter{page}{1}%
         * }
         *
         * %   Table of Contents/Figures/Tables    %
         *
         * \addto\captionsenglish{%
         * \renewcommand\contentsname{\color{mtc1} Table of Contents}}
         * \addto\captionsenglish{%
         * \renewcommand\listfigurename{\color{mtc1} Table of Figures}}
         * \addto\captionsenglish{%
         * \renewcommand\listtablename{\color{mtc1} List of Tables}}
         *
         * \renewcommand{\cftfigfont}{\normalsize\bfseries}
         * \renewcommand{\cftfigindent}{0pt}
         * \renewcommand{\cftfignumwidth}{4.25em}
         * \renewcommand{\cftfigpresnum}{Figure }
         * \renewcommand{\cftfigaftersnum}{:}
         *
         * \renewcommand{\cfttabfont}{\normalsize\bfseries}
         * \renewcommand{\cfttabindent}{0pt}
         * \renewcommand{\cfttabnumwidth}{4em}
         * \renewcommand{\cfttabpresnum}{Table }
         * \renewcommand{\cfttabaftersnum}{:}
         *
         * \renewcommand{\newline}{\vskip 0.1in}
         *
         * % 	Header and Footer Definitions   %
         *
         * \newcommand\@doctitleshort{}
         * \newcommand{\doctitleshort}[1]{\gdef\@doctitleshort{#1}}
         *
         * \pagestyle{fancy}
         * \fancyhf{}
         * \rhead{\@preparedon}
         * \lfoot{MTConnect \@docnum : \@doctitle { -} Version \@versionnum}
         * \rfoot{\thepage}
         * \renewcommand{\headrulewidth}{0pt}
         *
         * % 	Sections and Enumerate   %
         *
         * \setcounter{secnumdepth}{5}
         * \setcounter{tocdepth}{3}
         *
         * \makeatletter
         * \renewcommand\subparagraph{%
         * 	\@startsection {subparagraph}{5}{\z@ }{3.25ex \@plus 1ex
         * 	\@minus .2ex}{-1em}{\normalfont \normalsize \bfseries }}%
         * \makeatother
         *
         * \usepackage{float}
         *
         * \restylefloat{figure}
         * \restylefloat{table}
         *
         * \newif\iffigures
         * \newif\iftables
         *
         * \makeatletter
         * \AtEndDocument {%
         *     \if@filesw
         *        \ifnum\value{figure}=\z@ % no figures
         *           \immediate\write\@mainaux {\global\string\figuresfalse}%
         *        \else
         *           \immediate\write\@mainaux {\global\string\figurestrue}%
         *        \fi
         *        \ifnum\value{table}=\z@ % no tables
         *           \immediate\write\@mainaux {\global\string\tablesfalse}%
         *        \else
         *           \immediate\write\@mainaux {\global\string\tablestrue}%
         *        \fi
         *     \fi
         * }
         * \makeatother
         *
         * \definecolor{mtc1}{RGB}{43,105,145}
         * \sectionfont{\bfseries\color{mtc1}\Large}
         * \subsectionfont{\bfseries\color{mtc1}\large}
         * \subsubsectionfont{\bfseries\color{black}\large}
         * \paragraphfont{\bfseries\color{black}\normalsize}
         * \subparagraphfont{\bfseries\color{black}\normalsize}
         *
         * % 	Tables and Figures   %
         *
         * \definecolor{mtc2}{RGB}{0,128,128}
         * \newcommand{\tblh}[1]{\normalsize\textbf{\textcolor{white}{#1}}}
         *
         * \graphicspath{ {./figures/} }
         *
         * \newcommand{\figcap}[1]{\caption{\textbf{#1}}}
         * \captionsetup{labelfont=bf}
         *
         * \newcommand{\tabuheader}{\rowcolor{mtc2}\rowfont[c]{\fontsize{10pt}{12pt}\selectfont\bfseries\color{white}}}
         *
         * % 	Line Numbers   %
         *
         * \renewcommand\linenumberfont{\footnotesize\fontfamily{pcr}\selectfont}
         * \makeatletter
         * \patchcmd{\@startsection}{\@ifstar}{\nolinenumbers\@ifstar}{}{}
         * \patchcmd{\@xsect}{\ignorespaces}{\linenumbers\ignorespaces}{}{}
         * \makeatother
         * \linenumbers
         *
         * % 	Other Commands   %
         *
         * % Courier font selection:
         * \newcommand{\cfont}[1]{{\fontfamily{pcr}\selectfont #1}}
         * \newcommand{\literal}[1]{{\fontfamily{pcr}\selectfont #1}}
         * \newcommand{\xml}[1]{{\fontfamily{pcr}\selectfont #1}}
         * \newcommand{\deprecated}[1]{\sout{#1}}
         * \newcommand{\DEPRECATED}{\textbf{DEPRECATED }}
         * \newcommand{\DEPRECATIONWARNING}{\textbf{DEPRECATION WARNING }}
         * \newcommand{\WARNING}{\textbf{WARNING }}
         *
         * \newcommand{\notesign}{\textsuperscript{\textdagger}}
         * %create a loop if more are required
         *
         * % Requirement levels:
         * \newcommand{\must}{\textbf{MUST }}
         * \newcommand{\mustnot}{\textbf{MUST NOT }}
         * \newcommand{\should}{\textbf{SHOULD }}
         * \newcommand{\shouldnot}{\textbf{SHOULD NOT }}
         * \newcommand{\may}{\textbf{MAY }}
         * \newcommand{\maynot}{\textbf{MAY NOT }}
         * \newcommand{\shall}{\textbf{SHALL }}
         * \newcommand{\shallnot}{\textbf{SHALL NOT }}
         *
         * \newcommand{\NOT}{\textbf{NOT }}
         * % Mapping must, MUST, shall, SHALL to SHALL
         * \newcommand{\MUST}{\must}
         * \newcommand{\MUSTNOT}{\mustnot}
         *
         * \newcommand{\SHOULD}{\should}
         * \newcommand{\SHOULDNOT}{\shouldnot}
         * \newcommand{\MAY}{\may}
         * \newcommand{\MAYNOT}{\maynot}
         * \newcommand{\SHALL}{\shall}
         * \newcommand{\SHALLNOT}{\shallnot}
         *
         * % Formatting for cross-references:
         * \newcommand{\fig}[1]{\textit{Figure~\ref{fig:#1} }}
         * \newcommand{\sect}[1]{\textit{Section~\ref{sec:\detokenize{#1}} - \nameref{\detokenize{sec:#1}}}}
         * \newcommand{\tbl}[1]{\textit{Table~\ref{table:#1}}}
         * \newcommand{\apx}[1]{\textit{Appendix~\ref{appendix:#1}}}
         * \newcommand{\lst}[1]{\textit{Example~\ref{lst:#1}}}
         * \newcommand{\ver}[1]{\textit{MTConnect Version #1 }}
         *
         * % Format for terms
         * \newcommand{\term}[1]{\textit{#1}}
         *
         * % Formatting for code samples:
         * \newcommand{\code}{%
         * \lstset{basicstyle=\footnotesize\fontfamily{pcr}\selectfont,numbers=left,stepnumber=1,xleftmargin=0.25in,breaklines=true}}
         *
         * \definecolor{maroon}{rgb}{0.5,0,0}
         * \definecolor{darkgreen}{rgb}{0,0.5,0}
         *
         * % Glossaries
         *
         * \newglossary*{mtc}{MTConnect Terms}
         * \newglossary*{general}{General Terms}
         * \newglossary*{informationmodel}{Information Model Terms}
         * \newglossary*{protocol}{Protocol Terms}
         * \newglossary*{xml}{XML Terms}
         * \newglossary*{http}{HTTP Terms}
         * \newglossary*{conceptmodel}{Concept Model Terms}
         * \newglossary*{industrial}{Industrial Terms}
         *
         * \makeglossaries
         *
         * %Underlined headings (Example: scenarios in Part5)
         * \newcommand{\ulheading}[1]{\tab \uline{#1}}
         *
         * %indent/tab in tables
         * \newcommand{\tab}{\hspace{0.5cm}}
         *
         * % For acronyms, puts the long description first and then the acronym second.
         * \setabbreviationstyle[acronym]{long-short}
         *
         * \defglsentryfmt[general]{\term{\glsgenentryfmt}}
         * \defglsentryfmt[informationmodel]{\term{\glsgenentryfmt}}
         * \defglsentryfmt[protocol]{\term{\glsgenentryfmt}}
         * \defglsentryfmt[http]{\term{\glsgenentryfmt}}
         * \defglsentryfmt[xml]{\term{\glsgenentryfmt}}
         * \defglsentryfmt[conceptmodel]{\term{\glsgenentryfmt}}
         *
         * \renewcommand{\glsnamefont}[1]{%
         *   \glsifcategory{\glscurrententrylabel}{model}%
         *     {\cfont{#1}}%
         *     {\term{#1}}%
         * }
         *
         * \setglossarystyle{altlist}
         * \makeglossaries
         *
         * % Styles for OPC, UML, SysML 
         *
         * \usepackage{sty/tikz-uml}
         * \usetikzlibrary{positioning}
         * \usetikzlibrary{arrows,calc,decorations.markings,math,arrows.meta}
         *
         * \tikzumlset{fill class=white, fill template=white}
         *
         * \tikzstyle{tikzuml unidirectional association style}=%
         *    [color=\tikzumlDefaultDrawColor, {-{Stealth[inset=3pt,scale=2.5,angle'=45]}},%
         *    rounded corners]
         *
         * \tikzstyle{tikzuml inherit style}=%
         *    [color=\tikzumlDefaultDrawColor, {-{Stealth[inset=0pt,scale=2.5,fill=white,angle'=45]}},%
         *    rounded corners]
         *
         * \lstdefinelanguage{XML}
         * {
         *   basicstyle=\ttfamily\footnotesize,
         *   morestring=[b]",
         *   moredelim=[s][\bfseries\color{maroon}]{<}{\ },
         *   moredelim=[s][\bfseries\color{maroon}]{</}{>},
         *   moredelim=[l][\bfseries\color{maroon}]{/>},
         *   moredelim=[l][\bfseries\color{maroon}]{>},
         *   morecomment=[s]{<?}{?>},
         *   morecomment=[s]{<!--}{-->},
         *   commentstyle=\color{darkgreen},
         *   stringstyle=\color{blue},
         *   identifierstyle=\color{red}
         * }
         *
         * \newcommand{\block}[1]{\cfont{#1}}
         * \newcommand{\property}[1]{\cfont{#1}}
         * \newcommand{\operation}[1]{\cfont{#1}}
         *
         * \newenvironment{note}{}{}*/
        doc 
        /* {{term(AMT)}} owns the copyright in this MTConnect Specification or Material. {{term(AMT)}} grants to you a non-exclusive, non-transferable, revocable, non-sublicensable, fully-paid-up copyright license to reproduce, copy and redistribute this MTConnect Specification or Material, provided that you may only copy or redistribute the MTConnect Specification or Material in the form in which you received it, without modifications, and with all copyright notices and other notices and disclaimers contained in the MTConnect Specification or Material.
         *
         * If you intend to adopt or implement an MTConnect Specification or Material in a product, whether hardware, software or firmware, which complies with an MTConnect Specification, you shall agree to the MTConnect Specification Implementer License Agreement ("Implementer License") or to the MTConnect Intellectual Property Policy and Agreement ("IP Policy"'). The Implementer License and IP Policy each sets forth the license terms and other terms of use for MTConnect Implementers to adopt or implement the MTConnect Specifications, including certain license rights covering necessary patent claims for that purpose. These materials can be found at {{url(www.MTConnect.org)}}, or or by contacting {{url(mailto:info@MTConnect.org)}}. 
         *
         * MTConnect Institute and {{term(AMT)}} have no responsibility to identify patents, patent claims or patent applications which may relate to or be required to implement a Specification, or to determine the legal validity or scope of any such patent claims brought to their attention. Each MTConnect Implementer is responsible for securing its own licenses or rights to any patent or other intellectual property rights that may be necessary for such use, and neither {{term(AMT)}} nor MTConnect Institute have any obligation to secure any such rights.
         *
         * This Material and all MTConnect Specifications and Materials are provided "as is" and MTConnect Institute and {{term(AMT)}}, and each of their respective members, officers, affiliates, sponsors and agents, make no representation or warranty of any kind relating to these materials or to any implementation of the MTConnect Specifications or Materials in any product, including, without limitation, any expressed or implied warranty of noninfringement, merchantability, or fitness for particular purpose, or of the accuracy, reliability, or completeness of information contained herein. In no event shall MTConnect Institute or {{term(AMT)}} be liable to any user or implementer of MTConnect Specifications or Materials for the cost of procuring substitute goods or services, lost profits, loss of use, loss of data or any incidental, consequential, indirect, special or punitive damages or other direct damages, whether under contract, tort, warranty or otherwise, arising in any way out of access, use or inability to use the MTConnect Specification or other MTConnect Materials, whether or not they had advance notice of the possibility of such damage.
         *
         * The normative XMI is located at the following URL: [`MTConnectSysMLModel.xml`](https://model.mtconnect.org/MTConnectSysMLModel.xml)
         */
        doc 
        /* @manual{MTCPart1,
         *   title = {{MTConnect Standard Part 1.0 - Fundamentals}},
         *   %url = {http://bit.ly/2CaOlt1},
         *   label = {MTConnect Part 1.0},
         *   volume = {Part 1.0},
         *   version = {2.0},
         *   keywords = {MTC}
         *   }
         *
         * @manual{MTCPart2,
         *   title = {{MTConnect Standard: Part 2.0 - Device Information Model}},
         *   %url = {http://bit.ly/2OVfEy6},
         *   label = {MTConnect Part 2.0},
         *   volume = {Part 2.0},
         *   version = {2.0},
         *   keywords = {MTC}
         *   }
         *
         * @manual{MTCPart3,
         *   title = {{MTConnect Standard: Part 3.0 - Observation Information Model}},
         *   %url = {http://bit.ly/2pMob8q},
         *   label = {MTConnect Part 3.0},
         *   volume = {Part 3.0},
         *   version = {2.0},
         *   keywords = {MTC}
         *   }
         *
         * @manual{MTCPart4,
         *   title = {{MTConnect Standard: Part 4.0 - Asset Information Model}},
         *   %url = {http://bit.ly/2yyLc2D},
         *   label = {MTConnect Part 4.0},
         *   volume = {Part 4.0},
         *   version = {2.0},
         *   keywords = {MTC}
         *   }
         *
         * @manual{MTCPart5,
         *   title = {{MTConnect Standard: Part 5.0 - Interface Interaction Model}},
         *   %url = {http://bit.ly/2pPNGFY},
         *   label = {MTConnect Part 5.0},
         *   volume = {Part 5.0},
         *   version = {2.0},
         *   keywords = {MTC}
         *   }
         */
        doc 
        /* @article{Gerkey2004,
         *     title = {{A formal analysis and taxonomy of task allocation in multi-robot systems}},
         *     year = {2004},
         *     journal = {International Journal of Robotics Research},
         *     author = {Gerkey, Brian P. and Matari{\'{c}}, Maja J.},
         *     isbn = {0278-3649},
         *     doi = {10.1177/0278364904045564},
         *     issn = {02783649},
         *     pmid = {13688984},
         *     keywords = {Coordination, Multi-robot systems, Task allocation, Utility}
         * }
         *
         * @book{Gamma1994,
         *     title = {{Design Patterns: Elements of Reusable Object-Oriented Software}},
         *     year = {1994},
         *     author = {Gamma, Erich and Heml, Richard and Johnson, Ralph and Vlissides, John},
         *     pages = {107},
         *     publisher = {Addison Wesley},
         *     isbn = {ISBN 0-201-63361-2}
         * }
         *
         * @article{Birman1987,
         *     title = {{Exploiting virtual synchrony in distributed systems}},
         *     year = {1987},
         *     journal = {ACM SIGOPS Operating Systems Review},
         *     author = {Birman, K. and Joseph, T.},
         *     isbn = {089791242X},
         *     doi = {10.1145/37499.37515},
         *     issn = {01635980},
         *     pmid = {21463384}
         * }
         *
         * @misc{ISO2011,
         *     title = {{ISO/IEC 42010:2011}},
         *     year = {2011},
         *     booktitle = {Systems and software engineering - Architecture description},
         *     author = {{ISO}},
         *     number = {March},
         *     pages = {1--46},
         *     volume = {2011},
         *     url = {http://ieeexplore.ieee.org/xpl/articleDetails.jsp?tp=&arnumber=6129467&contentType=Standards&sortType=asc_p_Sequence&filter=AND(p_Publication_Number:6129465)},
         *     isbn = {978-0-7456-5060-9},
         *     doi = {10.1081/E-ELIS3-120044716},
         *     issn = {10655077},
         *     pmid = {15814772}
         * }
         *
         * @article{ISOInternationalOrganizationforStandardization2011,
         *     title = {{ISO/IEC/IEEE 42010:2011 - Systems and software engineering -- Architecture description}},
         *     year = {2011},
         *     journal = {ISOIECIEEE 420102011E Revision of ISOIEC 420102007 and IEEE Std 14712000},
         *     author = {{ISO (International Organization for Standardization)}},
         *     number = {March},
         *     pages = {1--46},
         *     volume = {2011},
         *     isbn = {VO -},
         *     doi = {10.1109/IEEESTD.2011.6129467},
         *     issn = {0028-0836}
         * }
         *
         * @phdthesis{Fielding2000ArchitecturalArchitectures,
         *     title = {{Architectural Styles and the Design of Network-based Software Architectures}},
         *     year = {2000},
         *     booktitle = {Doctoral thesis},
         *     author = {Fielding, Roy Thomas},
         *     isbn = {0599871180},
         *     doi = {10.1.1.91.2433},
         *     issn = {1098-6596},
         *     pmid = {25246403},
         *     arxivId = {arXiv:1011.1669v3}
         * }*/
        doc 
        /* % 					MTCONNECT DOCUMENT TEMPLATE 							%
         * % 	FILENAME: 		mtconnect.tex											%
         * %	VERSION:		0.1														%
         * % 	DATE:			02/13/2018												%
         * %	PORTED BY:		Moneer Helu												%
         * %	ADDRESS:		Engineering Laboratory									%
         * %					National Institute of Standards and Technology (NIST)	%
         * %					100 Bureau Drive										%
         * %					Mailstop 8260											%
         * %					Gaithersburg, MD 20899									%
         * %					United States of America								%
         * % 	EMAIL:			moneer.helu@nist.gov									%
         * % 	DESCRIPTION:	Template for MTConnect documentation;					%
         * % 					Initial attempt for testing and discussion				%
         * % 	USAGE:			\documentclass[options]{mtconnect}						%
         *
         *
         * \documentclass{mtconnect}	% Load mtconnect document class
         *
         * \input{acronyms.tex}
         * \input{glossary.tex}
         * %\addbibresource{references.bib}
         * \addbibresource{mtc.bib}
         *
         * %\hypersetup{draft} %to test without hyperlinks \hyperref
         * \begin{document}			% Begin document here
         *
         * % REQUIRED INITIAL INPUTS %
         *
         * \docnum{}							% Document "number"
         * \doctitle{}	% Full document title
         * \doctitleshort{}				% Shortened document title
         * \versionnum{}						% MTConnect version
         * \preparedfor{MTConnect Institute}		% Should not change!!!
         * \preparedfrom{\href{https://model.mtconnect.org/MTConnectSysMLModel.xml}{\texttt{MTConnectSysMLModel.xml}}}		% Model link
         * \preparedon{\today}			% Date prepared
         *
         * % FRONT MATTER (DO NOT CHANGE!!!) %
         *
         * \begin{nolinenumbers}
         * \maketitle				% Title page
         *
         * \pagenumbering{roman}
         *
         * % MTConnect Specification and Material Statement:
         * \textbf{\color{mtc1}\Large MTConnect Specification and Materials} \\
         *
         * \input{legal.tex}
         *
         * \clearpage
         * \tableofcontents
         * \thispagestyle{fancy}
         * \clearpage
         * \iffigures
         *    \listoffigures
         * \fi
         * \thispagestyle{fancy}
         * \clearpage
         * \iftables
         *    \listoftables
         * \fi
         * \end{nolinenumbers}
         *
         * \pagenumbering{arabic}
         *
         * % ENTER DOCUMENT CONTENT BELOW %
         *
         * \input{introduction.tex}
         *
         * \input{%MAIN%}
         *
         * \input{profile.tex}
         *
         * \input{appendix.tex}
         *
         * \end{document}
         */
        doc 
        /* {{appendix()}}
         * {{section*{Appendices}()}}
         * {{addcontentsline{toc}{section}{Appendices}()}}
         * {{renewcommand{\thesubsection}{\Alph{subsection}}()}}
         *
         * ## Bibliography
         *
         * Engineering Industries Association. EIA Standard - EIA-274-D, Interchangeable Variable, Block Data Format for Positioning, Contouring, and Contouring/Positioning Numerically Controlled Machines. Washington, D.C. 1979.
         *
         * ISO TC 184/SC4/WG3 N1089. ISO/DIS 10303-238: Industrial automation systems and integration  Product data representation and exchange  Part 238: Application Protocols: Application interpreted model for computerized numerical controllers. Geneva, Switzerland, 2004.
         *
         * International Organization for Standardization. ISO 14649: Industrial automation systems and integration – Physical device control – Data model for computerized numerical controllers – Part 10: General process data. Geneva, Switzerland, 2004.
         *
         * International Organization for Standardization. ISO 14649: Industrial automation systems and integration – Physical device control – Data model for computerized numerical controllers – Part 11: Process data for milling. Geneva, Switzerland, 2000.
         *
         * International Organization for Standardization. ISO 6983/1 – Numerical Control of machines – Program format and definition of address words – Part 1: Data format for positioning, line and contouring control systems. Geneva, Switzerland, 1982.
         *
         * Electronic Industries Association. ANSI/EIA-494-B-1992, 32 Bit Binary CL (BCL) and 7 Bit ASCII CL (ACL) Exchange Input Format for Numerically Controlled Machines. Washington, D.C. 1992.
         *
         * National Aerospace Standard. Uniform Cutting Tests - NAS Series: Metal Cutting Equipment Specifications. Washington, D.C. 1969.
         *
         * International Organization for Standardization. ISO 10303-11: 1994, Industrial automation systems and integration  Product data representation and exchange  Part 11: Description methods: The EXPRESS language reference manual. Geneva, Switzerland, 1994.
         *
         * International Organization for Standardization. ISO 10303-21: 1996, Industrial automation systems and integration -- Product data representation and exchange -- Part 21: Implementation methods: Clear text encoding of the exchange structure. Geneva, Switzerland, 1996.
         *
         * H.L. Horton, F.D. Jones, and E. Oberg. Machinery's Handbook. Industrial Press, Inc. New York, 1984.
         *
         * International Organization for Standardization. ISO 841-2001: Industrial automation systems and integration - Numerical control of machines - Coordinate systems and motion nomenclature. Geneva, Switzerland, 2001.
         *
         * ASME B5.57: Methods for Performance Evaluation of Computer Numerically Controlled Lathes and Turning Centers, 1998.
         *
         * ASME/ANSI B5.54: Methods for Performance Evaluation of Computer Numerically Controlled Machining Centers. 2005.
         *
         * OPC Foundation. OPC Unified Architecture Specification, Part 1: Concepts Version 1.00. July 28, 2006.
         *
         * IEEE STD 1451.0-2007, Standard for a Smart Transducer Interface for Sensors and Actuators – Common Functions, Communication Protocols, and Transducer Electronic Data Sheet (TEDS) Formats, IEEE Instrumentation and Measurement Society, TC-9, The Institute of Electrical and Electronics Engineers, Inc., New York, N.Y. 10016, SH99684, October 5, 2007.
         *
         * IEEE STD 1451.4-1994, Standard for a Smart Transducer Interface for Sensors and Actuators – Mixed-Mode Communication Protocols and Transducer Electronic Data Sheet (TEDS) Formats, IEEE Instrumentation and Measurement Society, TC-9, The Institute of Electrical and Electronics Engineers, Inc., New York, N.Y. 10016, SH95225, December 15, 2004. */
        doc 
        /* # MTConnect Specification and Material Statement
         *
         * {{input(legal.md)}}
         *
         * {{input(introduction.md)}}
         *
         * {{input(%MAIN%)}}
         *
         * {{input(profile.md)}}
         *
         * {{input(appendix.md)}}*/
    }
    comment /* Assets Appendix*/
    comment /* Assets Introduction*/
    comment /* Devices Introduction*/
    comment /* Devices Appendix*/
    comment /* Observations Introduction*/
    comment /* Observations Appendix*/
    comment /* Interfaces Introduction*/
    comment /* Fundamentals Appendix*/
    comment /* Fundamentals Introduction*/
    doc 
    /* {{newpage()}}
     *
     * ## XML Schema Diagrams
     *
     * See XML schemas for the MTConnect standard here: {{url(https://schemas.mtconnect.org/)}}.
     *
     * ### Assets Schema Diagrams
     *
     * See `Asset` element in `MTConnectAssets` schema.
     *
     * See `Description` element in `MTConnectAssets` schema.
     *
     * ### CuttingTool Schema Diagrams
     *
     * See `CuttingTool` element in `MTConnectAssets` schema.
     *
     * See `CuttingToolDefinition` element in `MTConnectAssets` schema.
     *
     * See `CuttingToolArchetypeReference` element in `MTConnectAssets` schema.
     *
     * ### CuttingToolLifeCycle Schema Diagrams
     *
     * See `CuttingToolLifeCycle` element in `MTConnectAssets` schema.
     *
     * See `CutterStatus` element in `MTConnectAssets` schema.
     *
     * See `Location` element in `MTConnectAssets` schema.
     *
     * See `Measurement` element in `MTConnectAssets` schema.
     *
     * See `ProcessFeedRate` element in `MTConnectAssets` schema.
     *
     * See `ProcessSpindleSpeed` element in `MTConnectAssets` schema.
     *
     * See `ReconditionCount` element in `MTConnectAssets` schema.
     *
     * See `ToolLife` element in `MTConnectAssets` schema.
     *
     * ### CuttingItem Schema Diagrams
     *
     * See `CuttingItems` element in `MTConnectAssets` schema.
     *
     * See `CuttingItem` element in `MTConnectAssets` schema.
     *
     * See `ItemLife` element in `MTConnectAssets` schema.
     *
     * ### ISO 13399 Diagrams
     *
     * #### Measurement Diagrams
     *
     * ![Cutting Tool Measurement 3](figures/Cutting%20Tool%20Measurement%203.png "Cutting Tool Measurement 3"){: width="0.8"}
     *
     * ![Cutting Tool Measurement 4](figures/Cutting%20Tool%20Measurement%204.png "Cutting Tool Measurement 4"){: width="0.8"}
     *
     * ![Cutting Tool Measurement 5](figures/Cutting%20Tool%20Measurement%205.png "Cutting Tool Measurement 5"){: width="0.8"}
     *
     * ![Cutting Tool Measurement 6](figures/Cutting%20Tool%20Measurement%206.png "Cutting Tool Measurement 6"){: width="0.8"}
     *
     * ![Cutting Tool Measurement 7](figures/Cutting%20Tool%20Measurement%207.png "Cutting Tool Measurement 7"){: width="0.8"}
     *
     * ![Cutting Tool Measurement 8](figures/Cutting%20Tool%20Measurement%208.png "Cutting Tool Measurement 8"){: width="0.8"}
     *
     * ### Cutting Tool Examples
     *
     * #### Shell Mill
     *
     * ![Shell Mill Side View](figures/Shell%20Mill%20Side%20View.png "Shell Mill Side View"){: width="0.8"}
     *
     * ![Indexable Insert Measurements](figures/Indexable%20Insert%20Measurements.png "Indexable Insert Measurements"){: width="0.8"}
     *
     * ~~~~xml
     * <?xml version="1.0" encoding="UTF-8"?>
     * <MTConnectAssets 
     * xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2
     * http://mtconnect.org/schemas/MTConnectAssets\_1.2.xsd">
     *   <Header creationTime="2011-05-11T13:55:22" 
     *   assetBufferSize="1024" sender="localhost"
     *   assetCount="2" version="1.2" instanceId="1234"/>
     *   <Assets>
     *   <CuttingTool serialNumber="1" toolId="KSSP300R4SD43L240" 
     *   timestamp="2011-05-11T13:55:22" assetId="KSSP300R4SD43L240.1" 
     *   manufacturers="KMT,Parlec">
     *     <CuttingToolLifeCycle>
     *     <CutterStatus><Status>NEW</Status></CutterStatus>
     *     <ProcessSpindleSpeed maximum="13300" 
     *     nominal="605">10000</ProcessSpindleSpeed>
     *     <ProcessFeedRate
     *     nominal="9.22">9.22</ProcessSpindleSpeed>
     *     <ConnectionCodeMachineSide>CV50
     *     </ConnectionCodeMachineSide>
     *     <Measurements>
     *       <BodyDiameterMax code="BDX">73.25
     *       </BodyDiameterMax>
     *       <OverallToolLength nominal="222.25" 
     *         minimum="221.996" maximum="222.504" 
     *         code="OAL">222.25</OverallToolLength>
     *       <UsableLengthMax code="LUX" nominal="82.55">82.55
     *       </UsableLengthMax>
     *       <CuttingDiameterMax code="DC" nominal="76.2" 
     *         maximum="76.213" minimum="76.187">76.2
     *       </CuttingDiameterMax>
     *       <BodyLengthMax code="LF" nominal="120.65" 
     *         maximum="120.904" minimum="120.404">120.65
     *       </BodyLengthMax>
     *       <DepthOfCutMax code="APMX" 
     *       nominal="60.96">60.95</DepthOfCutMax>
     *       <FlangeDiameterMax code="DF" 
     *         nominal="98.425">98.425</FlangeDiameterMax>
     *     </Measurements>
     *     <CuttingItems count="24">
     *       <CuttingItem indices="1-24" itemId="SDET43PDER8GB" 
     *         manufacturers="KMT" grade="KC725M">
     *         <Measurements>
     *           <CuttingEdgeLength code="L" nominal="12.7" 
     *             minimum="12.675" maximum="12.725">12.7
     *           </CuttingEdgeLength>
     *         <WiperEdgeLength code="BS" nominal=
     *           "2.56">2.56</WiperEdgeLength>
     *         <IncribedCircleDiameter code="IC"
     *           nominal="12.7">12.7
     *         </IncribedCircleDiameter>
     *         <CornerRadius code="RE" nominal="0.8">
     *           0.8</CornerRadius>
     *       </Measurements>
     *       </CuttingItem>
     *     </CuttingItems>
     *     </CuttingToolLifeCycle>
     *     </CuttingTool>
     *   </Assets>
     * </MTConnectAssets>
     * ~~~~
     * {: caption="Example for Indexable Insert Measurements"}
     *
     * {{pagebreak()}}
     *
     * #### Step Drill
     *
     * ![Step Mill Side View](figures/Step%20Mill%20Side%20View.png "Step Mill Side View"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-
     *   11T13:55:22" assetBufferSize="1024" 
     *   sender="localhost" assetCount="2" version="1.2" instanceId="1234"/>
     *   <Assets>
     *     <CuttingTool serialNumber="1 " toolId="B732A08500HP" 
     *     timestamp="2011-05-11T13:55:22" assetId="B732A08500HP " 
     *     manufacturers="KMT,Parlec">
     *       <Description>
     *         Step Drill - KMT, B732A08500HP Grade KC7315
     *         Adapter - Parlec, C50-M12SF300-6
     *       </Description>
     *       <CuttingToolLifeCycle>
     *         <CutterStatus><Status>NEW</Status></CutterStatus>
     *         <ProcessSpindleSpeed nominal="5893">5893</ProcessSpindleSpeed>
     *         <ProcessFeedRate nominal="2.5">2.5</ProcessFeedRate>
     *         <ConnectionCodeMachineSide>CV50 Taper</ConnectionCodeMachineSide>
     *         <Measurements>
     *           <BodyDiameterMax code="BDX">31.8</BodyDiameterMax>
     *           <BodyLengthMax code="LBX" nominal="120.825" maximum="126.325" 
     *           minimum="115.325">120.825</BodyLengthMax>
     *           <ProtrudingLength code="LPR" nominal="155.75" maximum="161.25" 
     *           minimum="150.26">155.75</ProtrudingLength>
     *           <FlangeDiameterMax code="DF" 
     *           nominal="98.425">98.425</FlangeDiameterMax>
     *           <OverallToolLength nominal="257.35" minimum="251.85" 
     *           maximum="262.85" code="OAL">257.35</OverallToolLength>
     *         </Measurements>
     *         <CuttingItems count="2">
     *           <CuttingItem indices="1" manufacturers="KMT" grade="KC7315">>
     *             <Measurements>
     *               <CuttingDiameter code="DC1" nominal="8.5" maximum="8.521" 
     *               minimum="8.506">8.5135</CuttingDiameter>
     *               <StepIncludedAngle code="STA1" nominal="90" maximum="91" 
     *               minimum="89">90</StepIncludedAngle>
     *               <FunctionalLength code="LF1" nominal="154.286" 
     *               minimum="148.786" 
     *               maximum="159.786">154.286</FunctionalLength>
     *               <StepDiameterLength code="SDL1" 
     *               nominal="9">9</StepDiameterLength>
     *               <PointAngle code="SIG" nominal="135" minimum="133" 
     *               maximum="137">135</PointAngle>
     *             </Measurements>
     *           </CuttingItem>
     *           <CuttingItem indices="2" manufacturers="KMT" grade="KC7315">>
     *             <Measurements>
     *               <CuttingDiameter code="DC2" nominal="12" maximum="12.011" 
     *               minimum="12">12</CuttingDiameter>
     *               <FunctionalLength code="LF2" nominal="122.493" 
     *               maximum="127.993" 
     *               minimum="116.993">122.493</FunctionalLength>
     *               <StepDiameterLength code="SDL2" 
     *               nominal="9">9</StepDiameterLength>
     *             </Measurements>
     *           </CuttingItem>
     *         </CuttingItems>
     *       </CuttingToolLifeCycle>
     *     </CuttingTool>
     *   </Assets>
     * </MTConnectAssets>
     * ~~~~
     * {: caption="Example for Step Mill Side View"}
     *
     * {{pagebreak()}}
     *
     * #### Shell Mill with Individual Loci
     *
     * ![Shell Mill with Explicate Loci](figures/Shell%20Mill%20with%20Explicate%20Loci.png "Shell Mill with Explicate Loci"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="KSSP300R4SD43L240" 
     *     timestamp="2011-05-11T13:55:22" assetId="KSSP300R4SD43L240.1" 
     *     manufacturers="KMT,Parlec">
     *       <Description>Keyway: 55 degrees</Description>
     *       <CuttingToolLifeCycle>
     *         <CutterStatus><Status>NEW</Status></CutterStatus>
     *         <Measurements>
     *           <UsableLengthMax code="LUX" 
     *           nominal="82.55">82.55</UsableLengthMax>
     *           <CuttingDiameterMax code="DC" nominal="76.2" maximum="76.213" 
     *           minimum="76.187">76.2</CuttingDiameterMax>
     *           <DepthOfCutMax code="APMX" nominal="60.96">60.95</DepthOfCutMax>
     *         </Measurements>
     *         <CuttingItems count="24">
     *           <CuttingItem indices="1" itemId="SDET43PDER8GB" 
     *           manufacturers="KMT">
     *             <Locus>FLUTE: 1, ROW: 1</Locus>
     *             <Measurements>
     *              <DriveAngle code="DRVA" nominal="55">55</DriveAngle>
     *            </Measurements>
     *           </CuttingItem>
     *           <CuttingItem indices="2-24" itemId="SDET43PDER8GB" 
     *           manufacturers="KMT">
     *             <Locus>FLUTE: 2-4, ROW: 1; FLUTE: 1-4, ROW 2-6</Locus>
     *           </CuttingItem>
     *         </CuttingItems>
     *       </CuttingToolLifeCycle>
     *     </CuttingTool>
     *   </Assets>
     * </MTConnectAssets>
     * ~~~~
     * {: caption="Example for Shell Mill with Explicate Loci"}
     *
     * {{pagebreak()}}
     *
     * #### Drill with Individual Loci
     *
     * ![Step Drill with Explicate Loci](figures/Step%20Drill%20with%20Explicate%20Loci.png "Step Drill with Explicate Loci"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="KSEM0781LD" 
     *     timestamp="2011-05-11T13:55:22" assetId="KSEM0781LD.1" manufacturers="KMT">
     *       <CuttingToolLifeCycle>
     *         <CutterStatus><Status>NEW</Status></CutterStatus>
     *         <ConnectionCodeMachineSide>HSK63A</ConnectionCodeMachineSide>
     *         <Measurements>
     *           <BodyDiameterMax code="BDX">52.75</BodyDiameterMax>
     *           <OverallToolLength nominal="172.29" 
     *           code="OAL">172.29</OverallToolLength>
     *           <UsableLengthMax code="LUX" nominal="49">49</UsableLengthMax>
     *           <FlangeDiameterMax code="DF" 
     *           nominal="62.94">62.94</FlangeDiameterMax>
     *         </Measurements>
     *         <CuttingItems count="3">
     *           <CuttingItem indices="1" itemId="KSEM0781LD" manufacturers="KMT" 
     *           grade="KC7015">
     *             <Locus>FLUTE: 1, ROW: 1</Locus>
     *             <Measurements>
     *          <FunctionalLength code="LF1" nominal="154.42">154.42</FunctionalLength>
     *          <CuttingDiameter code="DC1" nominal="19.844">19.844</CuttingDiameter>
     *          <PointAngle code="SIG" nominal="140">140</PointAngle>
     *          <ToolCuttingEdgeAngle code="KAPR1" nominal="45">45</ToolCuttingEdgeAngle>
     *          <StepDiameterLength code="SLD1" nominal="39.8">39.8</StepDiameterLength>
     *             </Measurements>
     *           </CuttingItem>
     *           <CuttingItem indices="2-3" itemId="TPMT-21.52-FP" 
     *           manufacturers="KMT" grade="KCM15">
     *             <Locus>FLUTE: 1-2, ROW: 2</Locus>
     *             <Measurements>
     *          <FunctionalLength code="LF2" nominal="112.9">119.2</FunctionalLength>
     *          <CuttingDiameter code="DC2" nominal="31">31</CuttingDiameter>
     *             </Measurements>
     *           </CuttingItem>
     *         </CuttingItems>
     *       </CuttingToolLifeCycle>
     *     </CuttingTool>
     *   </Assets>
     * </MTConnectAssets>
     * ~~~~
     * {: caption="Example for Step Drill with Explicate Loci"}
     *
     * {{pagebreak()}}
     *
     * #### Shell Mill with Different Inserts on First Row
     *
     * ![Shell Mill with Different Inserts on First Row](figures/Shell%20Mill%20with%20Different%20Inserts%20on%20First%20Row.png "Shell Mill with Different Inserts on First Row"){: width="0.8"}
     *
     * ~~~~xml
     * <?xml version="1.0" encoding="UTF-8"?>
     * <MTConnectAssets xmlns:m="urn:mtconnect.org:MTConnectAssets:1.2" 
     * xmlns="urn:mtconnect.org:MTConnectAssets:1.2" 
     * xmlns:xsi="http://www.w3.org/2001/XMLSchema-instance" 
     * xsi:schemaLocation="urn:mtconnect.org:MTConnectAssets:1.2 
     * http://mtconnect.org/schemas/MTConnectAssets\_1.2.xsd">
     *   <Header creationTime="2011-05-11T13:55:22" assetBufferSize="1024" 
     *   sender="localhost" assetCount="2" version="1.2" instanceId="1234"/>
     *   <Assets>
     *     <CuttingTool serialNumber="1" toolId="XXX" timestamp="2011-05-11T13:55:22" 
     *     assetId="XXX.1" manufacturers="KMT">
     *       <CuttingToolLifeCycle>
     *         <CutterStatus><Status>NEW</Status></CutterStatus>
     *         <Measurements>
     *           <DepthOfCutMax code="APMX" nominal="47.8">47.8</DepthOfCutMax>
     *           <CuttingDiameterMax code="DC" 
     *           nominal="50.8">50.8</CuttingDiameterMax>
     *           <UsableLengthMax code="LUX" 
     *           nominal="78.74">78.74</UsableLengthMax>
     *         </Measurements>
     *         <CuttingItems count="9">
     *           <CuttingItem indices="1-3" itemId="EDPT180564PDER-LD" 
     *           manufacturers="KMT">
     *             <Locus>FLUTE: 1-3, ROW: 1</Locus>
     *             <Measurements>
     *               <CornerRadius code="RE" nominal="6.25">6.35</CornerRadius>
     *             </Measurements>
     *           </CuttingItem>
     *           <CuttingItem indices="4-9" itemId="EDPT180508PDER-LD" 
     *           manufacturers="KMT">
     *             <Locus>FLANGE: 1-4, ROW: 2-3</Locus>
     *           </CuttingItem>
     *         </CuttingItems>
     *       </CuttingToolLifeCycle>
     *     </CuttingTool>
     *   </Assets>
     * </MTConnectAssets>
     * ~~~~
     * {: caption="Example for Shell Mill with Different Inserts on First Row"}
     *
     * ### File Schema Diagrams
     *
     * See `File` element in `MTConnectAssets` schema.
     *
     * ### RawMaterial Schema Diagrams
     *
     * See `RawMaterial` element in `MTConnectAssets` schema.
     *
     * ### QIFDocumentWrapper Schema Diagrams
     *
     * See `QIFDocumentWrapper` element in `MTConnectAssets` schema.*/
    doc 
    /* # Purpose of This Document
     *
     * This document, {{package(Asset Information Model)}} of the MTConnect Standard, details information that is common to all types of {{termplural(Asset)}}.  Part 4.0 of the MTConnect Standard provide semantic models for entities that are used in the manufacturing process, but are not considered to be a piece of equipment.  These entities are defined as {{termplural(Asset)}}.  These {{termplural(asset)}} may be removed from a piece of equipment without detriment to the function of the equipment and can be associated with other pieces of equipment during their lifecycle.  The data associated with these {{termplural(asset)}} may be retrieved from multiple sources that are each responsible for providing their knowledge of the {{term(asset)}}.
     *
     * # Terminology and Conventions
     *
     * Refer to {{package(Fundamentals)}} for a dictionary of terms, reserved language, and document conventions used in the MTConnect Standard.
     *
     * {{printglossary[title=General Terms, type=general]()}}
     * {{printglossary[title=Information Model Terms, type=informationmodel]()}}
     * {{printglossary[title=Protocol Terms, type=protocol]()}}
     * {{printglossary[title=HTTP Terms, type=http]()}}
     * {{printglossary[title=XML Terms, type=xml]()}}
     * {{printglossary[title=MTConnect Terms, type=conceptmodel]()}}
     *
     * {{printacronyms()}}
     *
     * {{printbibliography[title=MTConnect References,keyword=MTC]()}}
     *
     * {{printbibliography[title=Other References,notkeyword=MTC]()}}
     *
     * {{glsaddall()}}*/
    doc 
    /* # Purpose of This Document
     *
     * This document, {{package(Device Information Model)}} of the MTConnect Standard, establishes the rules and terminology to be used by designers to describe the function and operation of a piece of equipment and to define the data that is provided by an {{term(agent)}} from the equipment.  The {{term(Device Information Model)}}  also defines the structure for the {{term(response document)}} that is returned from an {{term(agent)}} in response to a {{term(probe request)}}. 
     *
     * In the MTConnect Standard, equipment represents any tangible property that is used in the operations of a manufacturing facility.  Examples of equipment are machine tools, ovens, sensor units, workstations, software applications, and bar feeders. 
     *
     * > Note: See {{package(Observation Information Model)}} of the MTConnect Standard for details on the {{term(response document)}} that are returned from an {{term(agent)}} in response to a {{term(sample request)}} or {{term(current request)}}.
     *
     * # Terminology and Conventions
     *
     * Refer to {{package(Fundamentals)}} for a dictionary of terms, reserved language, and document conventions used in the MTConnect Standard.
     *
     * {{printglossary[title=General Terms, type=general]()}}
     * {{printglossary[title=Information Model Terms, type=informationmodel]()}}
     * {{printglossary[title=Protocol Terms, type=protocol]()}}
     * {{printglossary[title=HTTP Terms, type=http]()}}
     * {{printglossary[title=XML Terms, type=xml]()}}
     * {{printglossary[title=MTConnect Terms, type=conceptmodel]()}}
     *
     * {{printacronyms()}}
     *
     * {{printbibliography[title=MTConnect References,keyword=MTC]()}}
     *
     * {{printbibliography[title=Other References,notkeyword=MTC]()}}
     *
     * {{glsaddall()}}*/
    doc 
    /* {{newpage()}} 
     *
     * ## XML Schema Diagrams
     *
     * See XML schemas for the MTConnect standard here: {{url(https://schemas.mtconnect.org/)}}.
     *
     * ### Components Schema Diagrams
     *
     * See `Components` element in `MTConnectDevices` schema.
     *
     * See `Description` element in `MTConnectDevices` schema.
     *
     * ### DataItems Schema Diagrams
     *
     * See `DataItems` element in `MTConnectDevices` schema.
     *
     * See `Source` element in `MTConnectDevices` schema.
     *
     * See `Constraints` element in `MTConnectDevices` schema.
     *
     * See `Filter` element in `MTConnectDevices` schema.
     *
     * See `Definition` element in `MTConnectDevices` schema.
     *
     * ### References Schema Diagrams
     *
     * See `References` element in `MTConnectDevices` schema.
     *
     * See `ComponentRef` element in `MTConnectDevices` schema.
     *
     * See `DataItemRef` element in `MTConnectDevices` schema.
     *
     * ### Configuration Schema Diagrams
     *
     * See `Configuration` element in `MTConnectDevices` schema.
     *
     * See `CoordinateSystem` element in `MTConnectDevices` schema.
     *
     * See `Motion` element in `MTConnectDevices` schema.
     *
     * See `Relationships` element in `MTConnectDevices` schema.
     *
     * See `ComponentRelationship` element in `MTConnectDevices` schema.
     *
     * See `DeviceRelationship` element in `MTConnectDevices` schema.
     *
     * See `SensorConfiguration` element in `MTConnectDevices` schema.
     *
     * See `SolidModel` element in `MTConnectDevices` schema.
     *
     * See `Specifications` element in `MTConnectDevices` schema.
     *
     * See `ProcessSpecification` element in `MTConnectDevices` schema.
     *
     * ## XML Examples
     *
     * ### Device Entity Hierarchy Example
     *
     * ~~~~xml
     * <Devices>
     *   <Device id="d1" name="M12346" uuid="M80104K162N">
     *     <Components>
     *     <Axes id="a" name="base">
     *     <Components>
     *       <Linear id="x" name="X"/>
     *       <Linear id="y" name="Y"/>
     *       <Linear id="z" name="Z"/>
     *       <Rotary id="ar" name="B"/>
     *       <Linear id="w" name="Z3" nativeName="W"/>
     *       <Rotary id="c" name="C"/>
     *     </Components>
     *     </Axes>
     *     <Controller id="cont" name="controller">
     *     <Components>
     *       <Path id="path1" name="path"/>
     *     </Components>
     *     </Controller>
     *     <Door id="door1" name="door"/>
     *     <Systems id="systems" name="systems">
     *     <Components>
     *       <WorkEnvelope id="we1" name="workenv">
     *       <Compositions>
     *         <Composition type="WORKPIECE" id="wp"/>
     *         <Composition type="TABLE" id="tbl"/>
     *       </Compositions>
     *       </WorkEnvelope>
     *       <Electric id="elec" name="electric"/>
     *       <Hydraulic id="hydraulic" name="hydraulic"/>
     *       <Coolant id="coolant" name="coolant"/>
     *       <Pneumatic id="pneumatic" name="pneumatic"/>
     *       <Lubrication id="lubrication" name="lubrication"/>
     *     </Components>
     *     </Systems>
     *     <Auxiliaries id="Aux" name="auxiliaries">
     *     <Components>
     *       <Environmental id="room" name="environmental"/>
     *     </Components>
     *     </Auxiliaries>
     *     <Resources id="resources" name="resources">
     *     <Components>
     *       <Personnel id="personnel" name="personnel"/>
     *       <Materials id="materials" name="materials">
     *       <Components>
     *         <Stock id="procstock" name="stock"/>
     *       </Components>
     *       <Materials/>
     *     </Components> 
     *     </Resources>
     *     </Components>
     *   </Device>
     * </Devices>
     * ~~~~
     * {: caption="Device Entity Hierarchy Example"}
     *
     * ### Component Example
     *
     * ~~~~xml
     * <Devices>
     *   <Device id="d1" name="M12346" uuid="M80104K162N">
     *     <Description manufacturer="Example_Corporation" 
     *       serialNumber="272237"> Mill w/SMooth-G
     *     </Description>
     *   <DataItems>
     *     <DataItem category="EVENT" id="avail" name="avail" type="AVAILABILITY"/>
     *     <DataItem category="EVENT" id="d1_asset_chg" name="asset_chg" type="ASSET_CHANGED"/>
     *     <DataItem category="EVENT" id="d1_asset_rem" name="asset_rem" type="ASSET_REMOVED"/>
     *   </DataItems>
     *     <Components>
     *     <Controller id="cont" name="controller">
     *       <DataItems>
     *       <DataItem category="EVENT" id="estop" name="estop" type="EMERGENCY_STOP"/>
     *       <DataItem category="CONDITION" id="logic_cond" type="LOGIC_PROGRAM"/>
     *       <DataItem category="CONDITION" id="cont_system" type="SYSTEM"/>
     *       <DataItem category="SAMPLE" id="cut_time" type="ACCUMULATED_TIME" units="SECOND"/>
     *     </DataItems>
     *     <Components>
     *       <Path id="path1" name="path">
     *         <DataItems>
     *         <DataItem category="EVENT" id="execution" name="execution" type="EXECUTION"/>
     *         <DataItem category="SAMPLE" id="cspeed" subType="ACTUAL" type="CUTTING_SPEED" units="MILLIMETER/SECOND"/>
     *         <DataItem category="CONDITION" id="path_system" type="SYSTEM"/>
     *         <DataItem category="EVENT" id="cvars" representation="DATA_SET" type="VARIABLE"/>
     *         <DataItem category="EVENT" id="woffset" representation="TABLE" type="WORK_OFFSET"/>
     *       </DataItems>
     *       </Path>
     *     </Components>
     *     </Controller>
     *   </Components>
     *   </Device>
     * </Devices>
     * ~~~~
     * {: caption="Component Example"}
     *
     * ### Component with Compositions Example
     *
     * In {{term(XML)}}, `Composition` types are represented differently than `Component` types. For `Component` types, the element name is Pascal Case of the `Component` type name. Whereas, the element name for all `Composition`types is `Composition` and the type is defined by the `type` attribute of the element (see example below).
     *
     * ~~~~xml
     * <WorkEnvelope id="we1" name="workenv">
     *   <DataItems>
     *     <DataItem category="CONDITION" id="hardware1" name="hardware1" type="HARDWARE"/>
     *   </DataItems>
     *   <Compositions>
     *   <Composition type="WORKPIECE" id="wp"/>
     *   <Composition type="TABLE" id="tbl"/>
     *   </Compositions>
     * </WorkEnvelope>
     * ~~~~
     * {: caption="Component with Compositions Example"}
     *
     * ### CoordinateSystem Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *   </Device>
     * </Devices>
     * ~~~~
     * {: caption="CoordinateSystem Example"}
     *
     * ### Motion Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *     <Components>
     *       <Axes id="a" name="base">
     *         <Components>
     *           <Linear id="x" name="X">
     *             <Configuration>
     *               <Motion id="xmotion" coordinateSystemIdRef="machcoord" type="PRISMATIC" actuation="DIRECT">
     *                 <Transformation>
     *                   <Translaton>300 915 590</Translaton>
     *                   <Rotation>0 0 0</Rotation>
     *                 </Transformation>
     *                 <Axis>1.0 0 0</Axis>
     *               </Motion>
     *             </Configuration>
     *           </Linear>
     *           <DataItems>
     *             <DataItem id="xtravel" type="SYSTEM" category="CONDITION">
     *           </DataItems>
     *         </Components>
     *       </Axes>
     *     </Components>
     *   </Device>
     * </Devices>
     * ~~~~
     * {: caption="Motion Example"}
     *
     * ### Relationship Example
     *
     * ~~~~xml
     * <Components>
     *   <Axes id="a" name="base">
     *     <Components>
     *       <Linear id="x" name="X">
     *         <Configuration>        
     *           <Relationships>
     *             <ComponentRelationship id="xpar" type="PARENT" idRef="we1"/>
     *           </Relationships>
     *         </Configuration>
     *       </Linear>
     *       <DataItems>
     *         <DataItem id="xtravel" type="SYSTEM" category="CONDITION">
     *       </DataItems>
     *     </Components>
     *   </Axes>
     *   <Systems id="systems" name="systems">
     *     <Components>
     *       <WorkEnvelope id="we1" name="workenv">
     *         <Compositions>
     *           <Composition type="WORKPIECE" id="wp"/>
     *           <Composition type="TABLE" id="tbl"/>
     *         </Compositions>
     *         <DataItems>
     *           <DataItem id="we1cond" type="SYSTEM" category="CONDITION">
     *         </DataItems>
     *       </WorkEnvelope>
     *     </Components>
     *   </Systems>
     * </Components>
     * ~~~~
     * {: caption="Relationship Example"}
     *       
     * ### SolidModel Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *     <Components>
     *       <Structures id="struct">
     *         <Configuration>
     *           <SolidModel id="model" mediaType="OBJ" href="/objs/mazak.obj" coordinateSystemIdRef="base">
     *             <Transformation>
     *               <Translation>0 860 0</Translation>
     *               <Rotation>-90 0 0</Rotation>
     *             </Transformation>
     *             <Scale>0.001 0.001 0.001</Scale>
     *           </SolidModel>
     *         </Configuration>
     *         <Components>
     *           <Structure id="xaxis" name="X_AXIS">
     *             <Configuration>
     *               <SolidModel id="x_model" mediaType="OBJ" itemRef="xaxis" solidModelIdRef="model" coordinateSystemIdRef="base"/>
     *             </Configuration>
     *             <DataItems>
     *               <DataItem type="SYSTEM" category="CONDITION" id="struct_cond"/>
     *             </DataItems>
     *           </Structure>
     *         </Components>
     *       </Structures>
     *     </Components>
     *   </Device>
     * </Devices>
     * ~~~~
     * {: caption="SolidModel Example"}
     *
     * ### Specification Example
     *
     * ~~~~xml
     * <Components>
     *   <Axes id="a" name="base">
     *     <Components>
     *       <Linear id="x" name="X">
     *         <Configuration>
     *           <Specifications>
     *             <Specification id="spec001" type="LENGTH" units="MILLIMETER">
     *               <Nominal>650</Nominal>
     *             </Specification>
     *             <Specification id="spec002" type="LINEAR_FORCE" units="NEWTON">
     *               <Maximum>5200</Maximum>
     *               <Minimum>0</Minimum>
     *             </Specification>
     *           </Specifications>
     *         </Configuration>
     *         <DataItems>
     *           <DataItem id="xtravel" type="SYSTEM" category="CONDITION">
     *         </DataItems>
     *       </Linear>
     *     </Components>
     *   </Axes>
     * </Components>
     * ~~~~
     * {: caption="Specification Example"}
     *
     * ### Example of sensing element provided as data item associated with a Component
     *
     * ~~~~xml
     * <Components>
     *   <Axes id="a" name="base"
     *     <Components>
     *       <Rotary id="c" name="C">
     *         <DataItems>
     *           <DataItem type="TEMPERATURE" id="servotemp4"
     *             category="SAMPLE" nativeUnits="CELSIUS"
     *             compositionId="Bmotor" units="CELSIUS"/>
     *           </DataItems>
     *       </Rotary>
     *     </Components>
     *   </Axes>
     * </Components>
     * ~~~~
     * {: caption="Example of sensing element provided as data item associated with a Component"}
     *
     * ### Example of Sensor for rotary axis
     *
     * ~~~~xml
     * <Components>
     *   <Axes id="a" name="base"
     *     <Components>
     *       <Rotary id="ar" name="B">
     *         <Components>
     *           <Sensor id="spdlm" name="Spindlemonitor">
     *             <DataItems>
     *               <DataItem type="DISPLACEMENT" id="cvib"
     *                 category="SAMPLE" name="Svib" 
     *                 units="MILLIMETER"/>
     *             </DataItems>
     *           </Sensor >
     *         <Components>
     *       </Rotary>
     *     </Components>
     *   </Axes>
     * </Components>
     * ~~~~
     * {: caption="Example of Sensor for rotary axis"}
     *
     * ### Example of sensor unit with sensing element
     *
     * ~~~~xml
     * <Axes id="a" name="base"
     *   <Components>
     *   <Sensor id="sens1" name="Sensorunit">
     *     <DataItems>
     *     <DataItem type="TEMPERATURE" id="sentemp"
     *       category="SAMPLE" name="Sensortemp" 
     *       units="CELSIUS"/> 
     *     </DataItems>
     *   </Sensor >
     *   <Linear id="x" name="X">
     *     <DataItems>
     *     <DataItem type="DISPLACEMENT" id="xvib"
     *       category="SAMPLE" name="xvib" 
     *       units="MILLIMETER">
     *       <Source componentId="sens1"/>
     *     </DataItem>
     *     </DataItems>
     *   </Rotary>
     *   <Linear id="y" name="Y">
     *     <DataItems>
     *     <DataItem type="DISPLACEMENT" id="yvib" 
     *       category="SAMPLE" name="yvib" 
     *       units="MILLIMETER">
     *       <Source componentId="sens1"/>
     *     </DataItem>
     *     </DataItems>
     *   </Linear>
     *   <Components>
     * </Axes>
     * ~~~~
     * {: caption="Example of sensor unit with sensing element"}
     *
     * ### Example of configuration data for Sensor
     *
     * ~~~~xml
     * <Sensor id="sensor" name="sensor">
     *   <Configuration>
     *     <SensorConfiguration>
     *       <FirmwareVersion>2.02</FirmwareVersion>
     *       <CalibrationDate>2010-05-16</CalibrationDate>
     *       <NextCalibrationDate>2010-05-16</NextCalibrationDate>
     *       <CalibrationInitials>WS</CalibrationInitials>
     *       <Channels>
     *         <Channel number="1" name="A/D:1">
     *           <Description>A/D With Thermister</Description>
     *         </Channel>
     *       </Channels>
     *     </SensorConfiguration>
     *   </Configuration>
     *   <DataItems>
     *     <DataItem category="CONDITION" id="sensorc" 
     *       name="sensorc" type="SYSTEM" />
     *     <DataItem category="SAMPLE" id="senv" name="sensorc"
     *       type="VOLTAGE_DC" units="VOLT" subType="ACTUAL" />
     *   </DataItems>
     * </Sensor>
     * ~~~~
     * {: caption="Example of configuration data for Sensor"}  */
    doc 
    /* # Purpose of This Document
     *
     * This document, {{package(Observation Information Model)}} of the MTConnect Standard, establishes the rules and terminology that describes the information returned by an {{term(MTConnect Agent)}} from a piece of equipment.  The {{term(Observation Information Model}} also defines, in {{package(Observation Information Model)}}, the structure for the {{termplural(response document)}} that are returned from an {{term(agent)}} in response to a {{term(sample request)}} or {{term(current request)}}.  
     *
     * {{package(Observation Information Model)}} is not a stand-alone document.   This document is used in conjunction with {{package(Fundamentals)}}  which defines the fundamentals of the operation of the MTConnect Standard and {{package(Device Information Model)}} that defines the semantic model representing the information that may be returned from a piece of equipment.
     *
     * > Note: {{package(Interface Interaction Model)}} provides details on extensions to the {{term(Observation Information Model)}} required to describe the interactions between pieces of equipment.
     *
     * In the MTConnect Standard, equipment represents any tangible property that is used in the operation of a manufacturing facility.  Examples of equipment are machine tools, ovens, sensor units, workstations, software applications, and bar feeders.
     *
     * # Terminology and Conventions
     *
     * Refer to {{package(Fundamentals)}} for a dictionary of terms, reserved language, and document conventions used in the MTConnect Standard.
     *
     * {{printglossary[title=General Terms, type=general]()}}
     * {{printglossary[title=Information Model Terms, type=informationmodel]()}}
     * {{printglossary[title=Protocol Terms, type=protocol]()}}
     * {{printglossary[title=HTTP Terms, type=http]()}}
     * {{printglossary[title=XML Terms, type=xml]()}}
     * {{printglossary[title=MTConnect Terms, type=conceptmodel]()}}
     *
     * {{printacronyms()}}
     *
     * {{printbibliography[title=MTConnect References,keyword=MTC]()}}
     *
     * {{printbibliography[title=Other References,notkeyword=MTC]()}}
     *
     * {{glsaddall()}}*/
    doc 
    /* {{newpage()}} 
     *
     * ## XML Schema Diagrams
     *
     * ### Observations Schema Diagrams
     *
     * See `Streams` element in `MTConnectStreams` schema.
     *
     * See `DeviceStream` element in `MTConnectStreams` schema.
     *
     * See `ComponentStream` element in `MTConnectStreams` schema.
     *
     * See `Sample` element in `MTConnectStreams` schema.
     *
     * See `Event` element in `MTConnectStreams` schema.
     *
     * See `Condition` element in `MTConnectStreams` schema.
     *
     * ### Representation Schema Diagrams
     *
     * See `AbsTimeSeries` element in `MTConnectStreams` schema.
     *
     * See `PartCountDiscrete` element in `MTConnectStreams` schema.
     *
     * See `VariableDataSet` element in `MTConnectStreams` schema.
     *
     * See `Entry` element in `MTConnectStreams` schema.
     *
     * See `WorkOffsetTable` element in `MTConnectStreams` schema.
     *
     * ## XML Examples
     *
     * ### DeviceStream Example
     *
     * ~~~~xml
     * <Streams>
     *   <DeviceStream name="M12346" uuid="M8010W4194N">
     *     <ComponentStream component="Device" name="M12346" componentId="d1">
     *       <Events>
     *         <Availability dataItemId="avail" sequence="156" timestamp="2021-10-01T14:26:38.668505Z">AVAILABLE</Availability>
     *         <AssetChanged assetType="CuttingTool" dataItemId="d1_asset_chg" sequence="75570" timestamp="2021-10-07T05:08:53.870206Z">M8010W4194N1.120</AssetChanged>
     *         <AssetRemoved assetType="CuttingTool" dataItemId="d1_asset_rem" sequence="140" timestamp="2021-10-01T11:40:08.101461Z">UNAVAILABLE</AssetRemoved>
     *       </Events>
     *     </ComponentStream>
     *     <ComponentStream component="Controller" name="controller" componentId="cont">
     *       <Events>
     *         <EmergencyStop dataItemId="estop" sequence="159" timestamp="2021-10-01T14:26:38.66869Z">ARMED</EmergencyStop>
     *       </Events>
     *       <Samples>
     *         <AccumulatedTime dataItemId="cut_time" sequence="75437" timestamp="2021-10-07T05:08:28.221704Z">1763070.0</AccumulatedTime>
     *       </Samples>
     *       <Condition>
     *         <Unavailable dataItemId="cont_system" sequence="72" timestamp="2021-10-11T21:04:03.251999Z" type="SYSTEM"/>
     *         <Warning dataItemId="cont_system" nativecode="313" nativeSeverity="50" sequence="75573" timestamp="2021-10-07T05:08:58.518317Z" type="LOGIC_PROGRAM">PALLET ARM DOWN RS. MALF.</Warning>
     *       </Condition>
     *     </ComponentStream>
     *     <ComponentStream component="Path" name="path" componentId="path1">
     *       <Events>
     *         <Execution dataItemId="execution" name="execution" sequence="222623" timestamp="2021-10-12T06:04:32.761198Z">INTERRUPTED</Execution>
     *         <VariableDataSet count="2" dataItemId="cvars" sequence="126513" timestamp="2021-10-12T03:57:31.106559Z">
     *           <Entry key="100">66.3314</Entry>
     *           <Entry key="101">167.2</Entry>
     *         </VariableDataSet>
     *         <WorkOffsetTable count="2" dataItemId="woffset" sequence="222101" timestamp="2021-10-12T06:04:11.990531Z">
     *           <Entry key="G53.1">
     *             <Cell key="X">1</Cell>
     *             <Cell key="Y">2</Cell>
     *             <Cell key="Z">3</Cell>
     *           </Entry>
     *           <Entry key="G53.2">
     *             <Cell key="X">4</Cell>
     *             <Cell key="Y">5</Cell>
     *             <Cell key="Z">6</Cell>
     *           </Entry>
     *         </WorkOffsetTable>
     *       </Events>
     *       <Samples>
     *         <CuttingSpeed dataItemId="cspeed" sequence="112" timestamp="2021-10-07T05:08:28.221704Z" subType="ACTUAL">UNAVAILABLE</CuttingSpeed>
     *       </Samples>
     *       <Condition>
     *         <Normal dataItemId="path_system" sequence="153" timestamp="2021-10-11T21:04:03.262845Z" type="SYSTEM"/>
     *       </Condition>
     *     </ComponentStream>
     *   </DeviceStream>
     * </Streams>
     * ~~~~
     * {: caption="DeviceStream Example"}
     *
     * ### Observations made for DataItem Example
     *
     * ~~~~xml
     * <Components>
     *   <Controller id="cont" name="controller">
     *       <DataItems>
     *       <DataItem category="EVENT" id="estop" name="estop" type="EMERGENCY_STOP"/>
     *     </DataItems>
     *   </Controller>
     * </Components>
     * ~~~~
     * {: caption="MTConnectDevices Response Document"}
     *
     * ~~~~xml
     * <ComponentStream component="Controller" name="controller" componentId="cont">
     *   <Events>
     *     <EmergencyStop dataItemId="estop" sequence="159" timestamp="2021-10-01T14:26:38.66869Z">ARMED</EmergencyStop>
     *   </Events>
     * </ComponentStream>
     * ~~~~
     * {: caption="MTConnectStreams Response Document"}
     *
     * ### Sample Example
     *
     * ~~~~xml
     * <Samples>
     *   <AccumulatedTime dataItemId="cut_time" sequence="75437" timestamp="2021-10-07T05:08:28.221704Z">1763070.0</AccumulatedTime>
     *   <CuttingSpeed dataItemId="cspeed" sequence="112" timestamp="2021-10-07T05:08:28.221704Z" subType="ACTUAL">UNAVAILABLE</CuttingSpeed>
     * </Samples>
     * ~~~~
     * {: caption="Sample Example"}
     *
     * ### Event Example
     *
     * ~~~~xml
     * <Events>
     *   <Availability dataItemId="avail" sequence="156" timestamp="2021-10-01T14:26:38.668505Z">AVAILABLE</Availability>
     *   <AssetRemoved assetType="CuttingTool" dataItemId="d1_asset_rem" sequence="140" timestamp="2021-10-01T11:40:08.101461Z">UNAVAILABLE</AssetRemoved>
     * </Events>
     * ~~~~
     * {: caption="Event Example"}
     *
     * ### Condition Example
     *
     * {{block(Condition)}} types are represented differently in {{term(XML)}} when compared to {{block(Sample)}} and {{block(Event)}} types. The element name is the {{term(condition state)}} of the {{block(Condition)}} type in Pascal Case. The name of the {{block(Condition)}} type is represented by the attribute `type`.
     *
     * If the {{term(condition state)}} is unavailable then the element name is represented by `Unavailable`.
     *
     * ~~~~xml
     * <Condition>
     *   <Unavailable dataItemId="cont_system" sequence="72" timestamp="2021-10-11T21:04:03.251999Z" type="SYSTEM"/>
     *   <Normal dataItemId="path_system" sequence="153" timestamp="2021-10-11T21:04:03.262845Z" type="SYSTEM"/>
     *   <Warning dataItemId="cont_system" nativecode="313" nativeSeverity="50" sequence="75573" timestamp="2021-10-07T05:08:58.518317Z" type="LOGIC_PROGRAM">PALLET ARM DOWN RS. MALF.</Warning>
     * </Condition>
     * ~~~~
     * {: caption="Condition Example"}
     *
     * ### DataSet Example
     *
     * ~~~~xml
     * <Events>
     *   <VariableDataSet count="2" dataItemId="cvars" sequence="126513" timestamp="2021-10-12T03:57:31.106559Z">
     *     <Entry key="100">66.3314</Entry>
     *     <Entry key="101">167.2</Entry>
     *   </VariableDataSet>
     * </Events>
     * ~~~~
     * {: caption="DataSet Example"}
     *
     * ### Table Example
     *
     * ~~~~xml
     * <Events>
     *   <WorkOffsetTable count="2" dataItemId="woffset" sequence="222101" timestamp="2021-10-12T06:04:11.990531Z">
     *     <Entry key="G53.1">
     *       <Cell key="X">1</Cell>
     *       <Cell key="Y">2</Cell>
     *       <Cell key="Z">3</Cell>
     *     </Entry>
     *     <Entry key="G53.2">
     *       <Cell key="X">4</Cell>
     *       <Cell key="Y">5</Cell>
     *       <Cell key="Z">6</Cell>
     *     </Entry>
     *   </WorkOffsetTable>
     * </Events>
     * ~~~~
     * {: caption="Table Example"}*/
    doc 
    /* # Purpose of This Document
     *
     * This document, {{package(Interface Interaction Model)}} of the MTConnect Standard, defines a structured data model used to organize information required to coordinate inter-operations between pieces of equipment.  
     *
     * This data model is based on an {{term(interaction model)}} that defines the exchange of information between pieces of equipment and is organized in the MTConnect Standard by {{block(Interfaces)}}.   
     *
     * {{block(Interfaces)}} is modeled as an extension to the {{term(Device Information Model)}} and {{term(Observation Information Model)}}.  {{block(Interfaces)}} leverages similar rules and terminology as those used to describe a component in the {{term(Device Information Model)}}.  {{block(Interfaces)}} also uses similar methods for reporting data to those used in the {{term(MTConnectStreams Response Document)}}.  
     *
     * As defined in {{package(Device Information Model)}}, {{block(Interfaces)}} {{termplural(organize)}} the {{block(Interface)}} types (see {{figure(Interfaces in Entity Hierarchy)}}).  Each individual {{block(Interface)}} contains data associated with the corresponding {{term(interface)}}.
     *
     * > Note: See {{package(Device Information Model)}} and {{package(Observation Information Model)}} of the MTConnect Standard for information on how {{block(Interfaces)}} is structured in the {{termplural(response document)}} which are returned from an {{term(agent)}} in response to a {{term(probe request)}}, {{term(sample request)}}, or {{term(current request)}}.
     *
     * # Terminology and Conventions
     *
     * Refer to {{package(Fundamentals)}} for a dictionary of terms, reserved language, and document conventions used in the MTConnect Standard.
     *
     * {{printglossary[title=General Terms, type=general]()}}
     * {{printglossary[title=Information Model Terms, type=informationmodel]()}}
     * {{printglossary[title=Protocol Terms, type=protocol]()}}
     * {{printglossary[title=HTTP Terms, type=http]()}}
     * {{printglossary[title=XML Terms, type=xml]()}}
     * {{printglossary[title=MTConnect Terms, type=conceptmodel]()}}
     *
     * {{printacronyms()}}
     *
     * {{printbibliography[title=MTConnect References,keyword=MTC]()}}
     *
     * {{printbibliography[title=Other References,notkeyword=MTC]()}}
     *
     * {{glsaddall()}}*/
    doc 
    /* {{newpage()}} 
     *
     * ## Fundamentals of Using XML to Encode Response Documents
     *
     * The MTConnect Standard specifies the structures and constructs that are used to encode {{termplural(response document)}}.  When these {{termplural(response document)}} are encoded using XML, there are additional rules defined by the XML standard that apply for creating an XML compliant document.  An implementer should refer to the W3C website for additional information on XML documentation and implementation details - http://www.w3.org/XML.
     *
     * The following provides specific terms and guidelines referenced in the MTConnect Standard for forming {{termplural(response document)}} with XML:  
     *
     *
     * * `tag`:  A `tag` is an XML construct that forms the foundation for an XML expression.  It defines the scope (beginning and end) of an XML expression.  The main types of tags are: 
     *
     * * `start-tag`:  Designates the beginning on an XML element; e.g., <{{term(element name)}}> 
     *
     * * `end-tag`:  Designates the end on an XML element; e.g., </{{term(element name)}}>. 
     *
     *
     * > Note: If an element has no {{termplural(child element)}} or {{term(CDATA)}}, the `end-tag` may be shortened to />.
     *
     *
     * * `Element`:  An element is an XML statement that is the primary building block for a document encoded using XML.  An element begins with a `start-tag` and ends with a matching `end-tag`.  The characters between the `start-tag` and the `end-tag` are the element's content.  The content may contain attributes, {{term(CDATA)}}, and/or other elements.  If the content contains additional elements, these elements are called {{termplural(child element)}}.
     *
     * An example would be:  <{{term(element name)}}>Content of the Element</{{term(element name)}}>.
     *
     * * {{term(child element)}}:  An XML element that is contained within a higher-level {{term(parent element)}}.  A {{term(child element)}} is also known as a sub-element.  XML allows an unlimited hierarchy of {{term(parent element)}}-{{term(child element)}} relationships that establishes the structure that defines how the various pieces of information in the document relate to each other.  A {{term(parent element)}} may have multiple associated {{termplural(child element)}}.
     *
     * * {{term(element name)}}:  A descriptive identifier contained in both the `start-tag` and `end-tag` that provides the name of an XML element.
     *
     * * `Attribute`:  A construct consisting of a name–value pair that provides additional information about that XML element.  The format for an attribute is `name="value"; where the value for the attribute is enclosed in a set of quotation (“) marks.  An XML attribute **MUST** only have a single value and each attribute can appear at most once in each element.  Also, each attribute **MUST** be defined in a {{term(schema)}} to either be required or optional.   
     *
     * * An example of attributes for an XML element is {{lst(example-of-attributes-for-an-element)}}:
     *
     * ~~~~xml
     * <DataItem category="SAMPLE" id="S1load"
     *   nativeUnits="PERCENT"  type="LOAD"
     *   units="PERCENT"/>
     * ~~~~
     * {: caption="Example of attributes for an element"}
     *
     * In this example, {{block(DataItem)}} is the {{term(element name)}}.  `category`, `id`, `nativeUnits`, `type`, and `units` are the names of the attributes.  “`SAMPLE`", “`S1load`", “`PERCENT`", “`LOAD`", and “`PERCENT`" are the values for each of the respective attributes.
     *
     * * {{term(CDATA)}}:  {{term(CDATA)}} is an XML term representing *Character Data*. *Character Data* contains a value(s) or text that is associated with an XML element.  {{term(CDATA)}} can be restricted to certain formats, patterns, or words.  
     *
     * An example of {{term(CDATA)}} associated with an XML element would be {{lst(example-of-cdata-associated-with-element)}}:
     *
     * ~~~~xml
     * <Message id="M1">This is some text</Message>
     * ~~~~
     * {: caption="Example of cdata associated with element"}
     *
     * In this example, `Message` is the {{term(element name)}} and `This is some text` is the {{term(CDATA)}}.
     *
     * * {{term(namespace)}}:  An XML {{term(namespace)}} defines a unique vocabulary for named elements and attributes in an XML document.  An XML document may contain content that is associated with multiple {{termplural(namespace)}}.  Each {{term(namespace)}} has its own unique identifier. 
     *
     * Elements and attributes are associated with a specific {{term(namespace)}} by placing a prefix on the name of the element or attribute that associates that name to a specific {{term(namespace)}}; e.g., `x:MyTarget` associates the element name `MyTarget` with the {{term(namespace)}} designated by `x:` (the prefix).
     *
     * {{termplural(namespace)}} are used to avoid naming conflicts within an XML document.  The naming convention used for elements and attributes may be associated with either the default {{term(namespace)}} specified in the header of an XML document or they may be associated with one or more alternate {{termplural(namespace)}}.  All elements or attributes associated with a {{term(namespace)}} that is not the default {{term(namespace)}}, must include a prefix (e.g., x:) as part of the name of the element or attribute to associate it with the proper {{term(namespace)}}.  See {{sect(Schema and Namespace Declaration Information)}} for details on the structure for XML headers.
     *
     * The names of the elements and attributes declared in a {{term(namespace)}} may be identified with a different prefix than the prefix that signifies that specific {{term(namespace)}}.  These prefixes are called {{term(namespace)}} aliases.  As an example, MTConnect Standard specific {{termplural(namespace)}} are designated as `m:` and the names of the elements and attributes defined in that {{term(namespace)}} have an alias prefix of `mt:` which designates these names as MTConnect Standard specific vocabulary; e.g., `mt:MTConnectDevices`. 
     *
     *
     * XML documents are encoded with a hierarchy of elements.  In general, XML elements may contain {{termplural(child element)}}, {{term(CDATA)}}, or both.  However, in the MTConnect Standard, an element **MUST NOT** contain mixed content; meaning it cannot contain both {{termplural(child element)}} and {{term(CDATA)}}. 
     *
     * The {{term(semantic data model)}} defined for each {{term(response document)}} specifies the elements and {{termplural(child element)}} that may appear in a document.  The {{term(semantic data model)}} also defines the number of times each element and {{term(child element)}} may appear in the document.
     *
     * {{lst(example-of-hierarchy-of-xml-elements)}} demonstrates the hierarchy of XML elements and {{termplural(child element)}} used to form an XML document:
     *
     * ~~~~xml
     * <Root Level>    (Parent Element)
     *   <First Level>  (Child Element to Root Level and 
     *   Parent Element to Second Level)
     *     <Second Level>  (Child Element to First Level
     *     and Parent Element to Third Level)
     *       <Third Level name="N1"></Third Level>  
     *       (Child Element to Second Level)
     *       <Third Level name="N2"></Third Level>  
     *       (Child Element to Second Level)
     *       <Third Level name="N3"></Third Level>  
     *       (Child Element to Second Level)
     *     </Second Level>   (end-tag for Second Level)
     *   </First Level>   (end-tag for First Level)
     * </Root Level>   (end-tag for Root Level)
     * ~~~~
     * {: caption="Example of hierarchy of XML elements"}
     *
     *
     * In the {{lst(example-of-hierarchy-of-xml-elements)}}, *Root Level* and *First Level* have one {{term(child element)}} (sub-elements) each and Second Level has three {{termplural(child element)}}; each called *Third Level*.  Each *Third Level* element has a different name attribute.  Each level in the structure is an element and each lower level element is a {{term(child element)}}.
     *
     * {{newpage()}}
     *
     * ## Schema and Namespace Declaration Information
     *
     * There are four pseudo-attributes typically included in the header of a {{term(response document)}} that declare the {{term(schema)}} and {{term(namespace)}} for the document.  Each of these pseudo-attributes provides specific information for a client software application to properly interpret the content of the {{term(response document)}}.
     *
     * The pseudo-attributes include:
     *
     * * `xmlns:xsi` – The `xsi` portion of this attribute name stands for {{term(XML Schema)}} instance.  An {{term(XML Schema)}} instance provides information that may be used by a software application to interpret XML specific information within a document.  See the W3C website for more details on `xmlns:xsi`.
     *
     * * `xmlns` – Declares the default {{term(namespace)}} associated with the content of the {{term(response document)}}.  The default {{term(namespace)}} is considered to apply to all elements and attributes whenever the name of the element or attribute does not contain a prefix identifying an alternate {{term(namespace)}}.
     *
     * The value of this attribute is an URN identifying the name of the file that defines the details of the {{term(namespace)}} content.  This URN provides a unique identify for the {{term(namespace)}}.
     *
     * * `xmlns:m` – Declares the MTConnect specific {{term(namespace)}} associated with the content of the {{term(response document)}}.  There may be multiple {{termplural(namespace)}} declared for an XML document.  Each may be associated to the default {{term(namespace)}} or it may be totally independent.  The `:m` designates that this is a specific MTConnect {{term(namespace)}} which is directly associated with the default {{term(namespace)}}.
     *
     *  
     * > Note:	See {{sect(Extensibility)}} for details regarding extended {{termplural(namespace)}}.
     *
     *
     * The value associated with this attribute is an URN identifying the name of the file that defines the details of the {{term(namespace)}} content.
     *
     * * `xsi:schemaLocation` -  Declares the name for the {{term(schema)}} associated with the {{term(response document)}} and the location of the file that contains the details of the {{term(schema)}} for that document.
     *
     * The value associated with this attribute has two parts:
     *
     *   * A URN identifying the name of the specific {{term(XML Schema)}} instance associated with the {{term(response document)}}.
     *
     *   * The path to the location where the file describing the specific {{term(XML Schema)}} instance is located.  If the file is located in the same root directory where the {{term(agent)}} is installed, then the local path MAY be declared.  Otherwise, a fully qualified URL must be declared to identify the location of the file.
     *
     *
     * > Note:	In the format of the value associated with `xsi:schemaLocation`, the URN and the path to the {{term(schema)}} file **MUST** be separated by a “space”.
     *
     *
     * In {{lst(example-of-schema-and-namespace-declaration)}}, the first line is the XML declaration.  The second line is a {{term(root element)}} called `MTConnectDevices`.  The remaining four lines are the pseudo-attributes of `MTCconnectDevices` that declare the XML {{term(schema)}} and {{term(namespace)}} associated with an {{term(MTConnectDevices Response Document)}}.
     *
     * ~~~~xml
     * <?xml version="1.0" encoding="UTF-8"?>
     *   <MTConnectDevices
     *    xmlns:xsi=http://www.w3.org/2001/XMLSchema-instance
     *    xmlns="urn:mtconnect.org:MTConnectDevices:1.3"
     *    xmlns:m="urn:mtconnect.org:MTConnectDevices:1.3"
     *    xsi:schemaLocation="urn:mtconnect.org:
     *     MTConnectDevices:1.3 /schemas/MTConnectDevices\_1.3.xsd">
     * ~~~~
     * {: caption="Example of schema and namespace declaration"}
     *
     * The format for the values provided for each of the pseudo-attributes **MUST** reference the {{term(semantic data model)}} (e.g., `MTConnectDevices`, `MTConnectStreams`, `MTConnectAssets`, or `MTConnectError`) and the version (i.e.; `1.1`, `1.2`, `1.3`, etc.) of the MTConnect Standard that depict the {{term(schema)}} and {{term(namespace)}}(s) associated with a specific {{term(response document)}}.
     *
     * When an implementer chooses to extend an MTConnect {{term(data model)}} by adding custom data types or additional {{termplural(structural element)}}, the {{term(schema)}} and {{term(namespace)}} for that {{term(data model)}} should be updated to reflect the additional content.  When this is done, the {{term(namespace)}} and {{term(schema)}} information in the header should be updated to reflect the URI for the extended {{term(namespace)}} and {{term(schema)}}. 
     *
     * {{newpage()}}
     *
     * ## Extensibility
     *
     * MTConnect is an extensible standard, which means that implementers **MAY** extend the {{termplural(data model)}} defined in the various sections of the MTConnect Standard to include information required for a specific implementation.  When these {{termplural(data model)}} are encoded using XML, the methods for extending these {{termplural(data model)}} are defined by the rules established for extending any XML schema (see the W3C website for more details on extending XML data models).
     *
     * The following are typical extensions that **MAY** be considered in the MTConnect {{termplural(data model)}}:
     *
     * * Additional `type` and `subtype` values for {{termplural(DataItem)}}.
     *
     * * Additional {{termplural(structural element)}} as containers.
     *
     * * Additional {{block(Composition)}} elements.
     *
     * * New {{block(Asset)}} types that are sub-typed from the abstract {{block(Asset)}} type.
     *
     * * {{termplural(child element)}} that may be added to specific XML elements contained within the {{termplural(MTConnect Information Model)}}.  These extended elements **MUST** be identified in a separate {{term(namespace)}}.
     *
     *
     * When extending an MTConnect {{term(data model)}}, there are some basic rules restricting changes to the MTConnect {{termplural(data model)}}.
     *
     * When extending an MTConnect {{term(data model)}}, an implementer:
     *
     * * **MUST NOT** add new value for category for {{termplural(DataItem)}},
     *
     * * **MUST NOT** add new {{termplural(root element)}},
     *
     * * **SHOULD NOT** add new {{term(top level)}} {{termplural(Component)}}, and
     *
     * * **MUST NOT** add any new attributes or include any sub-elements to {{block(Composition)}}.
     *
     * > Note:  Throughout the documents additional information is provided where extensibility may be acceptable or unacceptable to maintain compliance with the MTConnect Standard.
     *
     * When a {{term(schema)}} representing a {{term(data model)}} is extended, the {{term(schema)}} and {{term(namespace)}} declaration at the beginning of the corresponding {{term(response document)}} **MUST** be updated to reflect the new {{term(schema)}} and {{term(namespace)}} so that a client software application can properly validate the {{term(response document)}}.
     *
     * An XML example of a {{term(schema)}} and {{term(namespace)}} declaration, including an extended {{term(schema)}} and {{term(namespace)}}, is shown in {{lst(example-of-extended-schema-and-namespace-in-declaration)}}:
     *
     * ~~~~xml
     * <?xml version="1.0" encoding="UTF-8"?>
     *   <MTConnectDevices
     *    xmlns:xsi=http://www.w3.org/2001/XMLSchema-instance
     *    xmlns="urn:mtconnect.org:MTConnectDevices:1.3"
     *    xmlns:m="urn:mtconnect.org:MTConnectDevices:1.3"
     *    xmlns:x="urn:MyLocation:MyFile:MyVersion"
     *    xsi:schemaLocation="urn:MyLocation:MyFile:MyVersion
     *      /schemas/MyFileName.xsd" />
     * ~~~~
     * {: caption="Example of extended schema and namespace in declaration"}
     *
     * In this example:
     *
     * * `xmlns:x` is added in Line 6 to identify the {{term(XML Schema)}} instance for the extended {{term(schema)}}.   {{termplural(element name)}} identified with an "`x`" prefix are associated with this specific {{term(XML Schema)}} instance.
     *
     * > Note: The "`x`" prefix **MAY** be replaced with any prefix that the implementer chooses for identifying the extended {{term(schema)}} and {{term(namespace)}}.
     *
     * * `xsi:schemaLocation` is modified in Line 7 to associate the {{term(namespace)}} URN with the URL specifying the location of {{term(schema)}} file.
     *
     * * `MyLocation`, `MyFile`, `MyVersion`, and `MyFileName` in Lines 6 and 7 **MUST** be replaced by the actual name, version, and location of the extended {{term(schema)}}.
     *
     * When an extended {{term(schema)}} is implemented, each {{term(structural element)}}, {{term(DataItem)}}, and {{term(asset)}} defined in the extended {{term(schema)}} **MUST** be identified in each respective {{term(response document)}} by adding a prefix to the XML {{term(element name)}} associated with that {{term(structural element)}}, {{term(DataItem)}}, or {{term(asset)}}.  The prefix identifies the {{term(schema)}} and {{term(namespace)}} where that XML Element is defined. 
     */
    doc 
    /* # Overview of MTConnect
     *
     * MTConnect is a data and information exchange standard that is based on a {{term(data dictionary)}} of terms describing information associated with manufacturing operations.  The standard also defines a series of {{term(semantic data model)}} that provide a clear and unambiguous representation of how that information relates to a manufacturing operation.  The MTConnect Standard has been designed to enhance the data acquisition capabilities from equipment in manufacturing facilities, to expand the use of data driven decision making in manufacturing operations, and to enable software applications and manufacturing equipment to move toward a plug-and-play environment to reduce the cost of integration of manufacturing software systems.
     *
     * The MTConnect standard supports two primary communications methods - {{term(request and response)}} and {{term(publish and subscribe)}} type of communications.  The {{term(request and response)}} communications structure is used throughout this document to describe the functionality provided by MTConnect.  See {{sect(Streaming Data)}} for details describing the functionality of the {{term(publish and subscribe)}} communications structure available from an {{term(agent)}}. 
     *
     * Although the MTConnect Standard has been defined to specifically meet the requirements of the manufacturing industry, it can also be readily applied to other application areas as well.
     *
     * The MTConnect Standard is an open, royalty free standard – meaning that it is available for anyone to download, implement, and utilize in software systems at no cost to the implementer.
     *
     * The {{termplural(semantic data model)}} defined in the MTConnect Standard provide the information required to fully characterize data with both a clear and unambiguous meaning and a mechanism to directly relate that data to the manufacturing operation where the data originated.  Without a {{term(semantic data model)}}, client software applications must apply an additional layer of logic to raw data to convey this same level of meaning and relationship to manufacturing operations.  The approach provided in the MTConnect Standard for modeling and organizing data allows software applications to easily interpret data from a wide variety of data sources which reduces the complexity and effort to develop applications.
     *
     * The data and information from a broad range of manufacturing equipment and systems are addressed by the MTConnect Standard.  Where the {{term(data dictionary)}} and {{termplural(semantic data model)}} are insufficient to define some information within an implementation, an implementer may extend the {{term(data dictionary)}} and {{term(semantic data model)}} to address their specific requirements.  See {{sect(Extensibility)}} for guidelines related to extensibility of the MTConnect Standard.
     *
     * To assist in implementation, the MTConnect Standard is built upon the most prevalent standards in the manufacturing and software industries.  This maximizes the number of software tools available for implementation and provides the highest level of interoperability with other standards, software applications, and equipment used throughout manufacturing operations.  
     *
     * Current MTConnect implementations are based on HTTP as a transport protocol and XML as a language for encoding each of the {{termplural(semantic data model)}} into electronic documents.  All software examples provided in the various MTConnect Standard documents are based on these two core technologies.  
     *
     * The base functionality defined in the MTConnect Standard is the {{term(data dictionary)}} describing manufacturing information and the {{term(semantic data model)}}.  The transport protocol and the programming language used to represent or transfer the information provided by the {{termplural(semantic data model)}} are not restricted in the standard to HTTP and XML.  Therefore, other protocols and programming languages may be used to represent the semantic models and/or transport the information provided by these data models between an {{term(agent)}} (server) and a client software application as may be required by a specific implementation.
     *
     * > Note: The term "document" is used with different meanings in the MTConnect Standard:
     *
     * * Meaning 1:  The MTConnect Standard itself is comprised of multiple documents each addressing different aspects of the Standard.  Each document is referred to as a Part of the Standard.
     *
     * * Meaning 2:  In an MTConnect implementation, the electronic documents that are published from a data source and stored by an {{term(agent)}}.     
     *
     * * Meaning 3:  In an MTConnect implementation, the electronic documents generated by an {{term(agent)}} for transmission to a client software application. 
     *
     * The following will be used throughout the MTConnect Standard to distinguish between these different meanings for the term "document":
     *
     * * MTConnect Document(s) or Document(s) shall be used to refer to printed or electronic document(s) that represent a Part(s) of the MTConnect Standard.  
     *
     * * All reference to electronic documents that are received from a data source and stored in an {{term(agent)}} shall be referred to as {{term(document)}}(s) and are typically provided with a prefix identifier; e.g. asset document.
     *
     * * All references to electronic documents generated by an {{term(agent)}} and sent to a client software application shall be referred to as a {{term(response document)}}.  
     *
     * When used with no additional descriptor, the form "document" shall be used to refer to any printed or electronic document.
     *
     * Manufacturing software systems implemented utilizing MTConnect can be represented by a very simple structure as shown in {{figure(Basic MTConnect Implementation Structure)}}.
     *
     * ![Basic MTConnect Implementation Structure](figures/basic-mtconnect-implementation-structure.png "Basic MTConnect Implementation Structure"){: width="0.8"}
     *
     * The three basic modules that comprise a software system implemented using MTConnect are:
     *
     * * Equipment:  Any data source.  In the MTConnect Standard, equipment is defined as any tangible property that is used to equip the operations of a manufacturing facility.  Examples of equipment are machine tools, ovens, sensor units, workstations, software applications, and bar feeders.
     *
     * * Agent:  Software that collects data published from one or more piece(s) of equipment, organizes that data in a structured manner, and responds to requests for data from client software systems by providing a structured response in the form of a {{term(response document)}} that is constructed using the {{termplural(semantic data model)}} defined in the Standard. 
     *
     *     > Note: The {{term(agent)}} may be fully integrated into the piece of equipment or the {{term(agent)}} may be independent of the piece of equipment.  Implementation of an {{term(agent)}} is the responsibility of the supplier of the piece of equipment and/or the implementer of the {{term(agent)}}.
     *     
     * * Client Software Application:  Software that requests data from {{termplural(agent)}} and processes that data in support of manufacturing operations. 
     *
     * Based on {{figure(Basic MTConnect Implementation Structure)}}, it is important to understand that the MTConnect Standard only addresses the following functionality and behavior of an {{term(agent)}}:
     *
     * * the method used by a client software application to request information from an {{term(agent)}}.
     *
     * * the response that an {{term(agent)}} provides to a client software application.
     *
     * * a {{term(data dictionary)}} used to provide consistency in understanding the meaning of data reported by a data source.
     *
     * * the description of the {{termplural(semantic data model)}} used to structure {{termplural(response document)}} provided by an {{term(agent)}} to a client software application.
     *
     * These functions are the primary building blocks that define the base functional structure of the MTConnect Standard.
     *
     * There are a wide variety of data sources (equipment) and data consumption systems (client software systems) used in manufacturing operations.  There are also many different uses for the data associated with a manufacturing operation.  No single approach to implementing a data communication system can address all data exchange and data management functions typically required in the data driven manufacturing environment.  MTConnect has been uniquely designed to address this diversity of data types and data usages by providing different {{termplural(semantic data model)}} for different data application requirements:
     *
     * * Data Collection: The most common use of data in manufacturing is the collection of data associated with the production of products and the operation of equipment that produces those products.  The MTConnect Standard provides comprehensive {{termplural(semantic data model)}} that represent data collected from manufacturing operations.  These {{termplural(semantic data model)}} are detailed in {{package(Device Information Model)}} and {{package(Observation Information Model)}} of the MTConnect Standard.
     *
     * * Inter-operations Between Pieces of Equipment:  The MTConnect Standard provides an {{term(interaction model)}} that structures the information required to allow multiple pieces of equipment to coordinate actions required to implement manufacturing activities.  This {{term(interaction model)}} is an implementation of a {{term(request and response)}}  messaging structure.  This {{term(interaction model)}} is called {{block(Interfaces)}} which is detailed in {{package(Interface Interaction Model)}} of the MTConnect Standard.
     *
     * * Shared Data:  Certain information used in a manufacturing operation is commonly shared amongst multiple pieces of equipment and/or software applications.  This information is not typically "owned" by any one manufacturing resource.  The MTConnect Standard represents this information through a series of {{termplural(semantic data model)}} – each describing different types of information used in the manufacturing environment.  Each type of information is called an {{term(Asset)}}. {{termplural(Asset)}} are detailed in {{package(Asset Information Model)}}, and its sub-Parts, of the MTConnect Standard.
     *
     * # Purpose of This Document
     *
     * This document, {{package(Fundamentals)}} of the MTConnect  Standard, addresses two major topics relating to the MTConnect Standard.  The first sections of the document define the organization of the documents used to describe the MTConnect Standard; including the terms and terminology used throughout the Standard.  The balance of the document defines the following:
     *
     * * Operational concepts describing how an {{term(agent)}} should organize and structure data that has been collected from a data source.
     *
     * * Definition and structure of the {{termplural(response document)}} supplied by an {{term(agent)}}.
     *
     * * The protocol used by a client software application to communicate with an {{term(agent)}}.
     *
     *
     * # Terminology and Conventions
     *
     * This section provides a dictionary of terms, reserved language, and document conventions used in the MTConnect Standard.
     *
     * {{printglossary[title=General Terms, type=general]()}}
     * {{printglossary[title=Information Model Terms, type=informationmodel]()}}
     * {{printglossary[title=Protocol Terms, type=protocol]()}}
     * {{printglossary[title=HTTP Terms, type=http]()}}
     * {{printglossary[title=XML Terms, type=xml]()}}
     * {{printglossary[title=MTConnect Terms, type=conceptmodel]()}}
     *
     * {{printacronyms()}}
     *
     * {{printbibliography[title=MTConnect References,keyword=MTC]()}}
     *
     * {{printbibliography[title=Other References,notkeyword=MTC]()}}
     *
     * {{glsaddall()}}
     */
}
package 'WIP: Device Examples' {
    package PocketNC;
    package 'Kinematics Simulation' {
        part def robot7axes {
            part joint1 : XArm7Model::OriginProperty;
            part joint2 : XArm7Model::OriginProperty;
            private part joint3 : XArm7Model::OriginProperty;
            part joint4 : XArm7Model::OriginProperty;
            part joint5 : XArm7Model::OriginProperty;
            part joint6 : XArm7Model::OriginProperty;
            part joint7 : XArm7Model::OriginProperty;
            part Position : XArm7Model::Position;
            part angle1 : XArm7Model::Angle;
            part angle2 : XArm7Model::Angle;
            part angle3 : XArm7Model::Angle;
            part angle4 : XArm7Model::Angle;
            part angle5 : XArm7Model::Angle;
            part angle6 : XArm7Model::Angle;
            part angle7 : XArm7Model::Angle;
            binding bind joint1.origin.z = joint2.parentCoordinates.z;
            binding bind joint1.origin.y = joint2.parentCoordinates.y;
            binding bind joint1.origin.x = joint2.parentCoordinates.x;
            binding bind joint1.origin.c = joint2.parentCoordinates.c;
            binding bind joint1.origin.a = joint2.parentCoordinates.a;
            binding bind joint1.origin.b = joint2.parentCoordinates.b;
            binding bind joint2.origin.z = joint3.parentCoordinates.z;
            binding bind joint2.origin.y = joint3.parentCoordinates.y;
            binding bind joint2.origin.c = joint3.parentCoordinates.c;
            binding bind joint2.origin.x = joint3.parentCoordinates.x;
            binding bind joint2.origin.b = joint3.parentCoordinates.b;
            binding bind joint2.origin.a = joint3.parentCoordinates.a;
            binding bind joint3.origin.z = joint4.parentCoordinates.z;
            binding bind joint3.origin.y = joint4.parentCoordinates.y;
            binding bind joint3.origin.x = joint4.parentCoordinates.x;
            binding bind joint3.origin.c = joint4.parentCoordinates.c;
            binding bind joint3.origin.b = joint4.parentCoordinates.b;
            binding bind joint3.origin.a = joint4.parentCoordinates.a;
            binding bind joint4.origin.z = joint5.parentCoordinates.z;
            binding bind joint4.origin.y = joint5.parentCoordinates.y;
            binding bind joint4.origin.x = joint5.parentCoordinates.x;
            binding bind joint4.origin.c = joint5.parentCoordinates.c;
            binding bind joint4.origin.b = joint5.parentCoordinates.b;
            binding bind joint4.origin.a = joint5.parentCoordinates.a;
            binding bind joint5.origin.z = joint6.parentCoordinates.z;
            binding bind joint5.origin.y = joint6.parentCoordinates.y;
            binding bind joint5.origin.x = joint6.parentCoordinates.x;
            binding bind joint5.origin.c = joint6.parentCoordinates.c;
            binding bind joint5.origin.b = joint6.parentCoordinates.b;
            binding bind joint5.origin.a = joint6.parentCoordinates.a;
            binding bind joint6.origin.z = joint7.parentCoordinates.z;
            binding bind joint6.origin.y = joint7.parentCoordinates.y;
            binding bind joint6.origin.x = joint7.parentCoordinates.x;
            binding bind joint6.origin.c = joint7.parentCoordinates.c;
            binding bind joint6.origin.b = joint7.parentCoordinates.b;
            binding bind joint6.origin.a = joint7.parentCoordinates.a;
            binding bind Position.a = joint7.origin.a;
            binding bind Position.b = joint7.origin.b;
            binding bind Position.x = joint7.origin.x;
            binding bind Position.y = joint7.origin.y;
            binding bind Position.z = joint7.origin.z;
            binding bind Position.c = joint7.origin.c;
            binding bind angle2.angle = joint2.transform.'WIP: Device Examples'::'Kinematics Simulation'::XArm7Model::Transformation::ang;
            binding bind angle3.angle = joint3.transform.'WIP: Device Examples'::'Kinematics Simulation'::XArm7Model::Transformation::ang;
            binding bind angle5.angle = joint5.transform.'WIP: Device Examples'::'Kinematics Simulation'::XArm7Model::Transformation::ang;
            binding bind angle6.angle = joint6.transform.'WIP: Device Examples'::'Kinematics Simulation'::XArm7Model::Transformation::ang;
            binding bind angle7.angle = joint7.transform.'WIP: Device Examples'::'Kinematics Simulation'::XArm7Model::Transformation::ang;
            binding bind angle1.angle = joint1.transform.'WIP: Device Examples'::'Kinematics Simulation'::XArm7Model::Transformation::ang;
            binding bind angle4.angle = joint4.transform.'WIP: Device Examples'::'Kinematics Simulation'::XArm7Model::Transformation::ang;
            binding bind joint1.transform.'WIP: Device Examples'::'Kinematics Simulation'::XArm7Model::Transformation::angout = joint2.transform.'WIP: Device Examples'::'Kinematics Simulation'::XArm7Model::Transformation::angin;
            binding bind joint2.transform.'WIP: Device Examples'::'Kinematics Simulation'::XArm7Model::Transformation::angout = joint3.transform.'WIP: Device Examples'::'Kinematics Simulation'::XArm7Model::Transformation::angin;
            binding bind joint3.transform.'WIP: Device Examples'::'Kinematics Simulation'::XArm7Model::Transformation::angout = joint4.transform.'WIP: Device Examples'::'Kinematics Simulation'::XArm7Model::Transformation::angin;
            binding bind joint4.transform.'WIP: Device Examples'::'Kinematics Simulation'::XArm7Model::Transformation::angout = joint5.transform.'WIP: Device Examples'::'Kinematics Simulation'::XArm7Model::Transformation::angin;
            binding bind joint5.transform.'WIP: Device Examples'::'Kinematics Simulation'::XArm7Model::Transformation::angout = joint6.transform.'WIP: Device Examples'::'Kinematics Simulation'::XArm7Model::Transformation::angin;
            binding bind joint6.transform.'WIP: Device Examples'::'Kinematics Simulation'::XArm7Model::Transformation::angout = joint7.transform.'WIP: Device Examples'::'Kinematics Simulation'::XArm7Model::Transformation::angin;
        }
        package Simulation {
            occurrence def Kinematics;
        }
        package XArm7Model {
            part def OriginProperty {
                ref part parentCoordinates : ParentCoordinates;
                ref part origin : OriginPosition;
                ref part rotationVector : RotationVector;
                ref part translationVector : TranslationVector;
                assert constraint transform : Transformation;
                ref part unitVector : Axis;
                binding bind translationVector.y = transform.'WIP: Device Examples'::'Kinematics Simulation'::XArm7Model::Transformation::yt;
                binding bind translationVector.x = transform.'WIP: Device Examples'::'Kinematics Simulation'::XArm7Model::Transformation::xt;
                binding bind translationVector.z = transform.'WIP: Device Examples'::'Kinematics Simulation'::XArm7Model::Transformation::zt;
                binding bind parentCoordinates.x = transform.'WIP: Device Examples'::'Kinematics Simulation'::XArm7Model::Transformation::xin;
                binding bind parentCoordinates.y = transform.'WIP: Device Examples'::'Kinematics Simulation'::XArm7Model::Transformation::yin;
                binding bind parentCoordinates.z = transform.'WIP: Device Examples'::'Kinematics Simulation'::XArm7Model::Transformation::zin;
                binding bind parentCoordinates.a = transform.'WIP: Device Examples'::'Kinematics Simulation'::XArm7Model::Transformation::ain;
                binding bind parentCoordinates.b = transform.'WIP: Device Examples'::'Kinematics Simulation'::XArm7Model::Transformation::bin;
                binding bind parentCoordinates.c = transform.'WIP: Device Examples'::'Kinematics Simulation'::XArm7Model::Transformation::cin;
                binding bind rotationVector.x = transform.'WIP: Device Examples'::'Kinematics Simulation'::XArm7Model::Transformation::xr;
                binding bind rotationVector.y = transform.'WIP: Device Examples'::'Kinematics Simulation'::XArm7Model::Transformation::yr;
                binding bind rotationVector.z = transform.'WIP: Device Examples'::'Kinematics Simulation'::XArm7Model::Transformation::zr;
                binding bind origin.b = transform.'WIP: Device Examples'::'Kinematics Simulation'::XArm7Model::Transformation::bout;
                binding bind origin.a = transform.'WIP: Device Examples'::'Kinematics Simulation'::XArm7Model::Transformation::aout;
                binding bind origin.c = transform.'WIP: Device Examples'::'Kinematics Simulation'::XArm7Model::Transformation::cout;
                binding bind origin.x = transform.'WIP: Device Examples'::'Kinematics Simulation'::XArm7Model::Transformation::xout;
                binding bind origin.y = transform.'WIP: Device Examples'::'Kinematics Simulation'::XArm7Model::Transformation::yout;
                binding bind origin.z = transform.'WIP: Device Examples'::'Kinematics Simulation'::XArm7Model::Transformation::zout;
                binding bind unitVector.x = transform.'WIP: Device Examples'::'Kinematics Simulation'::XArm7Model::Transformation::xu;
                binding bind unitVector.y = transform.'WIP: Device Examples'::'Kinematics Simulation'::XArm7Model::Transformation::yu;
                binding bind unitVector.z = transform.'WIP: Device Examples'::'Kinematics Simulation'::XArm7Model::Transformation::zu;
            }
            part def ParentCoordinates :> Position;
            part def OriginPosition :> Position;
            part def RotationVector :> Vector;
            part def TranslationVector :> Vector;
            part def Position {
                attribute x : ScalarValues::Real default 0.0;
                attribute y : ScalarValues::Real default 0.0;
                attribute z : ScalarValues::Real default 0.0;
                attribute a : ScalarValues::Real default 0.0;
                attribute b : ScalarValues::Real default 0.0;
                attribute c : ScalarValues::Real default 0.0;
            }
            part def Vector {
                attribute x : ScalarValues::Real default 0.0;
                attribute y : ScalarValues::Real default 0.0;
                attribute z : ScalarValues::Real default 0.0;
            }
            constraint def Transformation {
                private attribute xin : ScalarValues::Real;
                private attribute yin : ScalarValues::Real;
                private attribute zin : ScalarValues::Real;
                private attribute xout : ScalarValues::Real;
                private attribute yout : ScalarValues::Real;
                private attribute zout : ScalarValues::Real;
                private attribute xt : ScalarValues::Real;
                private attribute yt : ScalarValues::Real;
                private attribute zt : ScalarValues::Real;
                private attribute xr : ScalarValues::Real;
                private attribute yr : ScalarValues::Real;
                private attribute zr : ScalarValues::Real;
                private attribute ain : ScalarValues::Real;
                private attribute bin : ScalarValues::Real;
                private attribute cin : ScalarValues::Real;
                private attribute aout : ScalarValues::Real;
                private attribute bout : ScalarValues::Real;
                private attribute cout : ScalarValues::Real;
                private attribute xu : ScalarValues::Real;
                private attribute yu : ScalarValues::Real;
                private attribute zu : ScalarValues::Real;
                private attribute ang : ScalarValues::Real;
                private attribute angin : ScalarValues::String;
                private attribute angout : ScalarValues::String;
            }
            part def Angle {
                attribute angle : ScalarValues::Real default 0.0;
            }
            part def Axis :> Vector;
        }
        package XArm7Instance;
    }
    package 'Mill w/SmoothG' {
        package Representation {
            part def Variable :> 'Observation Information Model'::Event;
            part def WorkOffsets :> 'Observation Information Model'::Event {
                attribute count [1] : Profile::DataTypes::integer {
                    doc /* number of {{block(Entry)}} elements for the {{block(Observation)}}.*/
                }
            }
            part def Temperature :> 'Observation Information Model'::Sample;
        }
    }
}
package 'MTConnect Device Validation Suite';
package 'Interface Interaction Model' {
    private package Signals {
        item def DISABLED;
        item def Activate;
        item def ENABLED;
        item def Success;
        item def Failure;
        item def FAIL;
        item def COMPLETE;
        item def NOT_READY;
        item def READY;
        item def ACTIVE;
    }
    package 'Interface Types' {
        part def BarFeederInterface :> Interface {
            doc 
            /* {{block(Interface)}} that coordinates the operations between a bar feeder and another piece of equipment.
             *
             * Bar feeder is a piece of equipment that pushes bar stock (i.e., long pieces of material of various shapes) into an associated piece of equipment – most typically a lathe or turning center.*/
        }
        part def MaterialHandlerInterface :> Interface {
            doc 
            /* {{block(Interface)}} that coordinates the operations between a piece of equipment and another associated piece of equipment used to automatically handle various types of materials or services associated with the original piece of equipment.
             *
             * A material handler is a piece of equipment capable of providing any one, or more, of a variety of support services for another piece of equipment or a process like:
             *
             * * Loading/unloading material or tooling
             * * Part inspection
             * * Testing
             * * Cleaning
             *
             * A robot is a common example of a material handler.*/
        }
        part def DoorInterface :> Interface {
            doc 
            /* {{block(Interface)}} that coordinates the operations between two pieces of equipment, one of which controls the operation of a door.
             *
             * The piece of equipment that is controlling the door **MUST** provide data item {{block(DoorState)}} as part of the set of information provided.*/
        }
        part def ChuckInterface :> Interface {
            doc 
            /* {{block(Interface)}} that coordinates the operations between two pieces of equipment, one of which controls the operation of a chuck.
             *
             * The piece of equipment that is controlling the chuck **MUST** provide the data item {{block(ChuckState)}} as part of the set of information provided.*/
        }
        doc 
        /* The abstract {{block(Interface)}} is realized by the following types listed in this section. 
         *
         * In order to implement the {{term(interaction model)}} for {{termplural(interface)}}, each piece of equipment associated with an {{term(interface)}} **MUST** provide the corresponding {{block(Interface)}} type. A piece of equipment **MAY** support any number of unique {{termplural(interface)}}.*/
        comment /* Interfaces for Device and Observation Information Models*/
        doc 
        /* The {{term(interaction model)}} for implementing {{termplural(interface)}} is defined in the MTConnect Standard as an extension to the {{term(Device Information Model)}} and {{term(Observation Information Model)}}.
         *
         * A piece of equipment **MAY** support multiple different {{termplural(interface)}}. Each piece of equipment supporting {{termplural(interface)}} **MUST** model the information associated with each {{term(interface)}} as an {{block(Interface)}} component.  {{block(Interface)}} is an abstract {{block(Component)}} and is realized by {{block(Interface)}} component types. 
         *
         * The {{figure(Interfaces in Entity Hierarchy)}} illustrates where an {{block(Interface)}} is modeled in the {{term(Device Information Model)}} for a piece of equipment.
         *
         * ![Interfaces in Entity Hierarchy](figures/Interfaces%20in%20Entity%20Hierarchy.png "Interfaces in Entity Hierarchy"){: width="0.8"}*/
    }
    abstract part def Interface :> 'Device Information Model'::Components::Component {
        doc /* abstract {{block(Component)}} that coordinates actions and activities between pieces of equipment.
         */
        private ref part isInterfaceOf : 'Device Information Model'::Device;
        part observesInterfaceState [1] : 'DataItem Types for Interface'::InterfaceState;
    }
    private part def Requester :> Interface {
        state def Request {
            state States {
                transition first $::States::StateAction::startShot then NOT_READY;
                transition first NOT_READY accept Signals::ENABLED then READY;
                transition first ACTIVE accept Signals::DISABLED then FAIL;
                transition first FAIL accept Signals::DISABLED then NOT_READY;
                transition first ACTIVE accept Signals::COMPLETE then READY;
                transition first FAIL then NOT_READY;
                transition first READY accept Signals::DISABLED then FAIL;
                transition first ACTIVE accept Signals::FAIL then FAIL::RECOVERY;
                transition first FAIL then READY;
                transition first ACTIVE do action : __unnamed53 then FAIL {
                    action def __unnamed53;
                }
                transition first READY then ACTIVE;
                state NOT_READY;
                state READY;
                state ACTIVE;
                state FAIL {
                    transition first $::States::StateAction::startShot accept Signals::FAIL then RECOVERY;
                    state RECOVERY {
                        action def recovery;
                        do action : recovery;
                    }
                }
            }
        }
        exhibit state : Request;
    }
    private part def Responder :> Interface {
        state def Response {
            item def InterfaceState;
            item def ENABLED;
            item def DISABLED;
            state States {
                transition first $::States::StateAction::startShot then NOT_READY;
                transition first NOT_READY accept ENABLED then READY;
                transition first READY accept Signals::ACTIVE then ACTIVE;
                transition first ACTIVE then COMPLETE;
                transition first COMPLETE then FAIL;
                transition first READY accept DISABLED then FAIL;
                transition first FAIL then READY;
                transition first FAIL then NOT_READY;
                transition first COMPLETE accept Signals::READY then READY;
                transition first ACTIVE accept Signals::NOT_READY then FAIL {
                    comment /**/
                }
                transition first ACTIVE accept DISABLED then FAIL;
                transition first ACTIVE accept Signals::FAIL then FAIL;
                transition first ACTIVE then FAIL;
                state NOT_READY;
                state READY;
                state ACTIVE;
                state COMPLETE;
                state FAIL {
                    transition first $::States::StateAction::startShot then RECOVERY;
                    state RECOVERY {
                        action def recovery;
                        do action : recovery;
                    }
                }
            }
        }
        exhibit state : Response;
    }
    package 'Operation and Error Recovery' {
        package 'Request and Response Failure Handling and Recovery' {
            doc 
            /* A significant feature of the {{term(request and response)}} {{term(interaction model)}} is the ability for either piece of equipment to detect a failure associated with either the {{term(request)}} or {{term(response)}} actions.  When either a failure or unexpected action occurs, the {{term(request)}} and the {{term(response)}} portion of the {{term(interaction model)}} can announce a `FAIL` state upon detecting a problem.  The following are graphical models describing multiple scenarios where either the {{term(requester)}} or {{term(responder)}} detects and reacts to a failure.  In these examples, either the {{term(requester)}} or {{term(responder)}} announces the detection of a failure by setting either the {{term(request)}} or the {{term(response)}} state to `FAIL`.  
             *
             * Once a failure is detected, the {{term(interaction model)}} provides information from each piece of equipment as they attempt to recover from a failure, reset all of their functions associated with the {{term(interface)}} to their original state, and return to normal operation.
             *
             * The following sections are scenarios that describe how pieces of equipment may react to different types of failures and how they indicate when they are again ready to request a service or respond to a request for service after recovering from those failures:
             *
             * ### Responder Fails Immediately
             *
             * In this scenario, a failure is detected by the {{term(responder)}} immediately after a {{term(request)}} for service has been initiated by the {{term(requester)}}.
             *
             * ![Responder Fails Immediately](figures/Responder%20Fails%20Immediately.png "Responder Fails Immediately"){: width="0.8"}
             *
             * In this case, the {{term(request)}} transitions to `ACTIVE` and the {{term(responder)}} immediately detects a failure before it can transition the {{term(response)}} state to `ACTIVE`.  When this occurs, the {{term(responder)}} transitions the {{term(response)}} state to `FAIL`.
             *
             * After detecting that the {{term(responder)}} has transitioned its state to `FAIL`, the {{term(requester)}} **MUST** change its state to `FAIL`.
             *
             * The {{term(requester)}}, as part of clearing a failure, resets any partial actions that were initiated and attempts to return to a condition where it is again ready to request a service.  If the recovery is successful, the {{term(requester)}} changes its state from `FAIL` to `READY`.  If for some reason the {{term(requester)}} cannot return to a condition where it is again ready to request a service, it transitions its state from `FAIL` to `NOT_READY`.
             *
             * The {{term(responder)}}, as part of clearing a failure, resets any partial actions that were initiated and attempts to return to a condition where it is again ready to perform a service.  If the recovery is successful, the {{term(responder)}} changes its {{term(response)}} state from `FAIL` to `READY`.  If for some reason the {{term(responder)}} is not again prepared to perform a service, it transitions its state from `FAIL` to `NOT_READY`.
             *
             * ### Responder Fails While Providing a Service
             *
             * This is the most common failure scenario.  In this case, the {{term(responder)}} will begin the actions required to provide a service.  During these actions, the {{term(responder)}} detects a failure and transitions its {{term(response)}} state to `FAIL`.
             *
             * ![Responder Fails While Providing a Service](figures/Responder%20Fails%20While%20Providing%20a%20Service.png "Responder Fails While Providing a Service"){: width="0.8"}
             *
             * When a {{term(requester)}} detects a failure of a {{term(responder)}}, it transitions it state from `ACTIVE` to `FAIL`.  
             *
             * The {{term(requester)}} resets any partial actions that were initiated and attempts to return to a condition where it is again ready to request a service.  If the recovery is successful, the {{term(requester)}} changes its state from `FAIL` to `READY` if the failure has been cleared and it is again prepared to request another service.  If for some reason the {{term(requester)}} cannot return to a condition where it is again ready to request a service, it transitions its state from `FAIL` to `NOT_READY`.
             *
             * The {{term(responder)}}, as part of clearing a failure, resets any partial actions that were initiated and attempts to return to a condition where it is again ready to perform a service.  If the recovery is successful, the {{term(responder)}} changes its {{term(response)}} state from `FAIL` to `READY` if it is again prepared to perform a service.  If for some reason the {{term(responder)}} is not again prepared to perform a service, it transitions its state from `FAIL` to `NOT_READY`.
             *
             * ### Requester Failure During a Service Request
             *
             * In this scenario, the {{term(responder)}} will begin the actions required to provide a service.  During these actions, the {{term(requester)}} detects a failure and transitions its {{term(request)}} state to `FAIL`.
             *
             * ![Requester Fails During a Service Request](figures/Requester%20Fails%20During%20a%20Service%20Request.png "Requester Fails During a Service Request"){: width="0.8"}
             *
             * When the {{term(responder)}} detects that the {{term(requester)}} has transitioned its {{term(request)}} state to `FAIL`, the {{term(responder)}} also transitions its {{term(response)}} state to `FAIL`. 
             *
             * The {{term(requester)}}, as part of clearing a failure, resets any partial actions that were initiated and attempts to return to a condition where it is again ready to request a service.  If the recovery is successful, the {{term(requester)}} changes its state from `FAIL` to `READY`.  If for some reason the {{term(requester)}} cannot return to a condition where it is again ready to request a service, it transitions its state from `FAIL` to `NOT_READY`.
             *
             * The {{term(responder)}}, as part of clearing a failure, resets any partial actions that were initiated and attempts to return to a condition where it is again ready to perform a service.  If the recovery is successful, the {{term(responder)}} changes its {{term(response)}} state from `FAIL` to `READY`.  If for some reason the {{term(responder)}} is not again prepared to perform a service, it transitions its state from `FAIL` to `NOT_READY`.
             *
             * ### Requester Changes to an Unexpected State While Responder is Providing a Service
             *
             * In some cases, a {{term(requester)}} may transition to an unexpected state after it has initiated a {{term(request)}} for service.  
             *
             * As demonstrated in {{figure(Requester Makes Unexpected State Change)}}, the {{term(requester)}} has initiated a {{term(request)}} for service and its {{term(request)}} state has been changed to `ACTIVE`.  The {{term(responder)}} begins the actions required to provide the service.  During these actions, the {{term(requester)}} transitions its {{term(request)}} state back to `READY` before the {{term(responder)}} can complete its actions.  This **SHOULD** be regarded as a failure of the {{term(requester)}}.
             *
             * ![Requester Makes Unexpected State Change](figures/Requester%20Makes%20Unexpected%20State%20Change.png "Requester Makes Unexpected State Change"){: width="0.8"}
             *
             * In this case, the {{term(responder)}} reacts to this change of state of the {{term(requester)}} in the same way as though the {{term(requester)}} had transitioned its {{term(request)}} state to `FAIL` (i.e., the same as in Scenario 3 above).
             *
             * At this point, the {{term(responder)}} then transitions its {{term(response)}} state to `FAIL`.
             *
             * The {{term(responder)}} resets any partial actions that were initiated and attempts to return to its original condition where it is again ready to perform a service.  If the recovery is successful, the {{term(responder)}} changes its {{term(response)}} state from `FAIL` to `READY`.  If for some reason the {{term(responder)}} is not again prepared to perform a service, it transitions its state from `FAIL` to `NOT_READY`.
             *
             * > Note: The same scenario exists if the {{term(requester)}} transitions its {{term(request)}} state to `NOT_READY`.  However, in this case, the {{term(requester)}} then transitions its {{term(request)}} state to `READY` after it resets all of its functions back to a condition where it is again prepared to make a {{term(request)}} for service.
             *
             *
             * ### Responder Changes to an Unexpected State While Providing a Service
             *
             * Similar to Scenario 5, a {{term(responder)}} may transition to an unexpected state while providing a service.  
             *
             * As demonstrated in {{figure(Responder Makes Unexpected State Change)}}, the {{term(responder)}} is performing the actions to provide a service and the {{term(response)}} state is `ACTIVE`.  During these actions, the {{term(responder)}} transitions its state to `NOT_READY` before completing its actions.  This should be regarded as a failure of the {{term(responder)}}.
             *
             * ![Responder Makes Unexpected State Change](figures/Responder%20Makes%20Unexpected%20State%20Change.png "Responder Makes Unexpected State Change"){: width="0.8"}
             *
             * Upon detecting an unexpected state change of the {{term(responder)}}, the {{term(requester)}} transitions its state to `FAIL`.  
             *
             * The {{term(requester)}} resets any partial actions that were initiated and attempts to return to a condition where it is again ready to request a service.  If the recovery is successful, the {{term(requester)}} changes its state from `FAIL` to `READY`.  If for some reason the {{term(requester)}} cannot return to a condition where it is again ready to request a service, it transitions its state from `FAIL` to `NOT_READY`.
             *
             * Since the {{term(responder)}} has failed to an invalid state, the condition of the {{term(responder)}} is unknown.  Where possible, the {{term(responder)}} should try to reset to an initial state. 
             *
             * The {{term(responder)}}, as part of clearing the cause for the change to the unexpected state, should attempt to reset any partial actions that were initiated and then return to a condition where it is again ready to perform a service.  If the recovery is successful, the {{term(responder)}} changes its {{term(response)}} state from the unexpected state to `READY`.  If for some reason the {{term(responder)}} is not again prepared to perform a service, it maintains its state as `NOT_READY`. 
             *
             * ### Responder or Requester Become UNAVAILABLE or Experience a Loss of Communication
             *
             * In this scenario, a failure occurs in the communications connection between the {{term(responder)}} and {{term(requester)}}.  This failure may result from the {{block(InterfaceState)}} from either piece of equipment returning a value of `UNAVAILABLE` or one of the pieces of equipment does not provide a heartbeat within the desired amount of time (See {{package(Fundamentals)}} for details on heartbeat).   
             *
             * ![Requester - Responder Communication Failure 1](figures/Requester%20-%20Responder%20Communication%20Failure%201.png "Requester - Responder Communication Failure 1"){: width="0.8"}
             *
             * ![Requester - Responder Communication Failure 2](figures/Requester%20-%20Responder%20Communication%20Failure%202.png "Requester - Responder Communication Failure 2"){: width="0.8"}
             *
             * When one of these situations occurs, each piece of equipment assumes that there has been a failure of the other piece of equipment.
             *
             * When normal communications are re-established, neither piece of equipment should assume that the {{term(request and response)}} state of the other piece of equipment remains valid.  Both pieces of equipment should set their state to `FAIL`.
             *
             * The {{term(requester)}}, as part of clearing its `FAIL` state, resets any partial actions that were initiated and attempts to return to a condition where it is again ready to request a service.  If the recovery is successful, the {{term(requester)}} changes its state from `FAIL` to `READY`.  If for some reason the {{term(requester)}} cannot return to a condition where it is again ready to request a service, it transitions its state from `FAIL` to `NOT_READY`.
             *
             * The {{term(responder)}}, as part of clearing its `FAIL` state, resets any partial actions that were initiated and attempts to return to a condition where it is again ready to perform a service.  If the recovery is successful, the {{term(responder)}} changes its {{term(response)}} state from `FAIL` to `READY`.  If for some reason the {{term(responder)}} is not again prepared to perform a service, it transitions its state from `FAIL` to `NOT_READY`.
             */
        }
        doc 
        /* The {{term(request and response)}} state model implemented for {{termplural(interface)}} may also be represented by a graphical model.  The scenario in {{figure(Success Scenario)}} demonstrates the state transitions that occur during a successful {{term(request)}} for service and the resulting {{term(response)}} to fulfill that service {{term(request)}}. 
         *
         * ![Success Scenario](figures/Success%20Scenario.png "Success Scenario"){: width="0.8"}*/
    }
    package 'DataItem Types for Interface' {
        part def MaterialFeed :> 'Observation Information Model'::Event {
            doc /* {{def(InterfaceEventEnum::MATERIAL_FEED)}}*/
            constant attribute type :>> MaterialChange::type : Profile::DataTypes::InterfaceEventEnum :> MaterialChange::type default type::MATERIAL_FEED;
            constant attribute subType :>> subType : Profile::DataTypes::DataItemSubTypeEnum :> subType;
        }
        part def MaterialChange :> 'Observation Information Model'::Event {
            doc /* {{def(InterfaceEventEnum::MATERIAL_CHANGE)}}*/
            constant attribute type :>> MaterialFeed::type : Profile::DataTypes::InterfaceEventEnum :> MaterialFeed::type default type::MATERIAL_CHANGE;
            constant attribute subType :>> subType : Profile::DataTypes::DataItemSubTypeEnum :> subType;
        }
        part def 'MaterialChange.Request' :> MaterialChange {
            doc /* operating state of the {{term(request)}} to change the type of material or product being loaded or fed to a piece of equipment.*/
            constant attribute subType :>> MaterialFeed::subType : Profile::DataTypes::DataItemSubTypeEnum :> MaterialFeed::subType default subType::REQUEST;
            attribute result [0..1] :>> result : Profile::DataTypes::RequestStateEnum :> result;
        }
        part def 'MaterialChange.Response' :> MaterialChange {
            doc /* operating state of the {{term(response)}} to a {{term(request)}} to change the type of material or product being loaded or fed to a piece of equipment.*/
            constant attribute subType :>> MaterialFeed::subType : Profile::DataTypes::DataItemSubTypeEnum :> MaterialFeed::subType default subType::RESPONSE;
            attribute result [0..1] :>> result : Profile::DataTypes::ResponseStateEnum :> result;
        }
        part def 'MaterialFeed.Request' :> MaterialFeed {
            doc /* operating state of the {{term(request)}} to advance material or feed product to a piece of equipment from a continuous or bulk source.*/
            constant attribute subType :>> MaterialFeed::subType : Profile::DataTypes::DataItemSubTypeEnum :> MaterialFeed::subType default subType::REQUEST;
            attribute result [0..1] :>> result : Profile::DataTypes::RequestStateEnum :> result;
        }
        part def 'MaterialFeed.Response' :> MaterialFeed {
            doc /* operating state of the {{term(response)}} to a {{term(request)}} to advance material or feed product to a piece of equipment from a continuous or bulk source.*/
            constant attribute subType :>> MaterialFeed::subType : Profile::DataTypes::DataItemSubTypeEnum :> MaterialFeed::subType default subType::RESPONSE;
            attribute result [0..1] :>> result : Profile::DataTypes::ResponseStateEnum :> result;
        }
        part def MaterialRetract :> 'Observation Information Model'::Event {
            doc /* {{def(InterfaceEventEnum::MATERIAL_RETRACT)}}*/
            constant attribute type :>> MaterialFeed::type : Profile::DataTypes::InterfaceEventEnum :> MaterialFeed::type default type::MATERIAL_RETRACT;
            constant attribute subType :>> subType : Profile::DataTypes::DataItemSubTypeEnum :> subType;
        }
        part def 'MaterialRetract.Request' :> MaterialRetract {
            doc /* operating state of the {{term(request)}} to remove or retract material or product.*/
            constant attribute subType :>> MaterialFeed::subType : Profile::DataTypes::DataItemSubTypeEnum :> MaterialFeed::subType default subType::REQUEST;
            attribute result [0..1] :>> result : Profile::DataTypes::RequestStateEnum :> result;
        }
        part def 'MaterialRetract.Response' :> MaterialRetract {
            doc /* operating state of the {{term(response)}} to a {{term(request)}} to remove or retract material or product.*/
            constant attribute subType :>> MaterialFeed::subType : Profile::DataTypes::DataItemSubTypeEnum :> MaterialFeed::subType default subType::RESPONSE;
            attribute result [0..1] :>> result : Profile::DataTypes::ResponseStateEnum :> result;
        }
        part def MaterialLoad :> 'Observation Information Model'::Event {
            doc /* {{def(InterfaceEventEnum::MATERIAL_LOAD)}}*/
            constant attribute type :>> MaterialFeed::type : Profile::DataTypes::InterfaceEventEnum :> MaterialFeed::type default type::MATERIAL_LOAD;
            constant attribute subType :>> subType : Profile::DataTypes::DataItemSubTypeEnum :> subType;
        }
        part def 'MaterialLoad.Request' :> MaterialLoad {
            doc /* operating state of the {{term(request)}} to load a piece of material or product.*/
            constant attribute subType :>> MaterialFeed::subType : Profile::DataTypes::DataItemSubTypeEnum :> MaterialFeed::subType default subType::REQUEST;
            attribute result [0..1] :>> result : Profile::DataTypes::RequestStateEnum :> result;
        }
        part def 'MaterialLoad.Response' :> MaterialLoad {
            doc /* operating state of the {{term(response)}} to a {{term(request)}} to load a piece of material or product.*/
            constant attribute subType :>> MaterialFeed::subType : Profile::DataTypes::DataItemSubTypeEnum :> MaterialFeed::subType default subType::RESPONSE;
            attribute result [0..1] :>> result : Profile::DataTypes::ResponseStateEnum :> result;
        }
        part def MaterialUnload :> 'Observation Information Model'::Event {
            doc /* {{def(InterfaceEventEnum::MATERIAL_UNLOAD)}}*/
            constant attribute type :>> MaterialFeed::type : Profile::DataTypes::InterfaceEventEnum :> MaterialFeed::type default type::MATERIAL_UNLOAD;
            constant attribute subType :>> subType : Profile::DataTypes::DataItemSubTypeEnum :> subType;
        }
        part def 'MaterialUnload.Request' :> MaterialUnload {
            doc /* operating state of the {{term(request)}} to unload a piece of material or product.*/
            constant attribute subType :>> MaterialFeed::subType : Profile::DataTypes::DataItemSubTypeEnum :> MaterialFeed::subType default subType::REQUEST;
            attribute result [0..1] :>> result : Profile::DataTypes::RequestStateEnum :> result;
        }
        part def 'MaterialUnload.Response' :> MaterialUnload {
            doc /* operating state of the {{term(response)}} to a {{term(request)}} to unload a piece of material or product.*/
            constant attribute subType :>> MaterialFeed::subType : Profile::DataTypes::DataItemSubTypeEnum :> MaterialFeed::subType default subType::RESPONSE;
            attribute result [0..1] :>> result : Profile::DataTypes::ResponseStateEnum :> result;
        }
        part def OpenChuck :> 'Observation Information Model'::Event {
            doc /* {{def(InterfaceEventEnum::OPEN_CHUCK)}}*/
            constant attribute type :>> MaterialFeed::type : Profile::DataTypes::InterfaceEventEnum :> MaterialFeed::type default type::OPEN_CHUCK;
            constant attribute subType :>> subType : Profile::DataTypes::DataItemSubTypeEnum :> subType;
        }
        part def 'OpenChuck.Request' :> OpenChuck {
            doc /* operating state of the {{term(request)}} to open a chuck.*/
            constant attribute subType :>> MaterialFeed::subType : Profile::DataTypes::DataItemSubTypeEnum :> MaterialFeed::subType default subType::REQUEST;
            attribute result [0..1] :>> result : Profile::DataTypes::RequestStateEnum :> result;
        }
        part def 'OpenChuck.Response' :> OpenChuck {
            doc /* operating state of the {{term(response)}} to a {{term(request)}} to open a chuck.*/
            constant attribute subType :>> MaterialFeed::subType : Profile::DataTypes::DataItemSubTypeEnum :> MaterialFeed::subType default subType::RESPONSE;
            attribute result [0..1] :>> result : Profile::DataTypes::ResponseStateEnum :> result;
        }
        part def OpenDoor :> 'Observation Information Model'::Event {
            doc /* {{def(InterfaceEventEnum::OPEN_DOOR)}}*/
            constant attribute type :>> MaterialFeed::type : Profile::DataTypes::InterfaceEventEnum :> MaterialFeed::type default type::OPEN_DOOR;
            constant attribute subType :>> subType : Profile::DataTypes::DataItemSubTypeEnum :> subType;
        }
        part def 'OpenDoor.Request' :> OpenDoor {
            doc /* operating state of the {{term(request)}} to open a door.*/
            constant attribute subType :>> MaterialFeed::subType : Profile::DataTypes::DataItemSubTypeEnum :> MaterialFeed::subType default subType::REQUEST;
            attribute result [0..1] :>> result : Profile::DataTypes::RequestStateEnum :> result;
        }
        part def 'OpenDoor.Response' :> OpenDoor {
            doc /* operating state of the {{term(response)}} to a {{term(request)}} to open a door.*/
            constant attribute subType :>> MaterialFeed::subType : Profile::DataTypes::DataItemSubTypeEnum :> MaterialFeed::subType default subType::RESPONSE;
            attribute result [0..1] :>> result : Profile::DataTypes::ResponseStateEnum :> result;
        }
        part def PartChange :> 'Observation Information Model'::Event {
            doc /* {{def(InterfaceEventEnum::PART_CHANGE)}}*/
            constant attribute type :>> MaterialFeed::type : Profile::DataTypes::InterfaceEventEnum :> MaterialFeed::type default type::PART_CHANGE;
            constant attribute subType :>> subType : Profile::DataTypes::DataItemSubTypeEnum :> subType;
        }
        part def 'PartChange.Request' :> PartChange {
            doc /* operating state of the {{term(request)}} to change the part or product associated with a piece of equipment to a different part or product.*/
            constant attribute subType :>> MaterialFeed::subType : Profile::DataTypes::DataItemSubTypeEnum :> MaterialFeed::subType default subType::REQUEST;
            attribute result [0..1] :>> result : Profile::DataTypes::RequestStateEnum :> result;
        }
        part def 'PartChange.Response' :> PartChange {
            doc /* operating state of the {{term(response)}} to a {{term(request)}} to change the part or product associated with a piece of equipment to a different part or product.*/
            constant attribute subType :>> MaterialFeed::subType : Profile::DataTypes::DataItemSubTypeEnum :> MaterialFeed::subType default subType::RESPONSE;
            attribute result [0..1] :>> result : Profile::DataTypes::ResponseStateEnum :> result;
        }
        part def CloseDoor :> 'Observation Information Model'::Event {
            doc /* {{def(InterfaceEventEnum::CLOSE_DOOR)}}*/
            constant attribute type :>> MaterialFeed::type : Profile::DataTypes::InterfaceEventEnum :> MaterialFeed::type default type::CLOSE_DOOR;
            constant attribute subType :>> subType : Profile::DataTypes::DataItemSubTypeEnum :> subType;
        }
        part def 'CloseDoor.Request' :> CloseDoor {
            doc /* operating state of the {{term(request)}} to close a door.*/
            constant attribute subType :>> MaterialFeed::subType : Profile::DataTypes::DataItemSubTypeEnum :> MaterialFeed::subType default subType::REQUEST;
            attribute result [0..1] :>> result : Profile::DataTypes::RequestStateEnum :> result;
        }
        part def 'CloseDoor.Response' :> CloseDoor {
            doc /* operating state of the {{term(response)}} to a {{term(request)}} to close a door.*/
            constant attribute subType :>> MaterialFeed::subType : Profile::DataTypes::DataItemSubTypeEnum :> MaterialFeed::subType default subType::RESPONSE;
            attribute result [0..1] :>> result : Profile::DataTypes::ResponseStateEnum :> result;
        }
        part def CloseChuck :> 'Observation Information Model'::Event {
            doc /* {{def(InterfaceEventEnum::CLOSE_CHUCK)}}*/
            constant attribute type :>> MaterialFeed::type : Profile::DataTypes::InterfaceEventEnum :> MaterialFeed::type default type::CLOSE_CHUCK;
            constant attribute subType :>> subType : Profile::DataTypes::DataItemSubTypeEnum :> subType;
        }
        part def 'CloseChuck.Request' :> CloseChuck {
            doc /* operating state of the {{term(request)}} to close a chuck.*/
            constant attribute subType :>> MaterialFeed::subType : Profile::DataTypes::DataItemSubTypeEnum :> MaterialFeed::subType default subType::REQUEST;
            attribute result [0..1] :>> result : Profile::DataTypes::RequestStateEnum :> result;
        }
        part def 'CloseChuck.Response' :> CloseChuck {
            doc /* operating state of the {{term(response)}} to a {{term(request)}} to close a chuck.*/
            constant attribute subType :>> MaterialFeed::subType : Profile::DataTypes::DataItemSubTypeEnum :> MaterialFeed::subType default subType::RESPONSE;
            attribute result [0..1] :>> result : Profile::DataTypes::ResponseStateEnum :> result;
        }
        part def InterfaceState :> 'Observation Information Model'::Event {
            doc 
            /* {{def(InterfaceEventEnum::INTERFACE_STATE)}}
             *
             * When the {{block(InterfaceState)}} is `DISABLED`, the state of all data items that are specific for the {{term(interaction model)}} associated with that {{block(Interface)}} **MUST** be set to `NOT_READY`.*/
            constant attribute type :>> MaterialFeed::type : Profile::DataTypes::InterfaceEventEnum :> MaterialFeed::type default type::INTERFACE_STATE;
            attribute result [0..1] :>> result : Profile::DataTypes::InterfaceStateEnum :> result;
        }
        doc 
        /* Each {{block(Interface)}} contains data items which are used to communicate information required to execute the {{term(interface)}}. When these data items are read by another piece of equipment, that piece of equipment can then determine the actions that it may take based upon that data.
         *
         * {{block(InterfaceState)}} is a data item specifically defined for {{termplural(interface)}}.  It defines the operational state of the {{term(interface)}}.  This is an indicator identifying whether the {{term(interface)}} is functioning or not. See {{sect(InterfaceState)}} for complete semantic details.
         *
         * Some data items **MAY** be directly associated with the {{block(Interface)}} element and others will be organized by a {{block(References)}} element. It is up to an implementer to determine which additional data items are required for a particular {{term(interface)}}.
         *
         * ### Specific Data Items for the Interaction Model for Interface
         *
         * A special set of data items have been defined to be used in conjunction with {{block(Interface)}}. They provide information from a piece of equipment to {{term(request)}} a service to be performed by another associated piece of equipment; and for the associated piece of equipment to indicate its progress in performing its {{term(response)}} to the {{term(request)}} for service.  .
         *
         * Many of the data items describing the services associated with an {{term(interface)}} are paired to describe two distinct actions – one to {{term(request)}} an action to be performed and a second to reverse the action or to return to an original state.  For example, a {{block(DoorInterface)}} will have two actions {{block(OpenDoor)}} and {{block(CloseDoor)}}. An example of an implementation of this would be a robot that indicates to a machine that it would like to have a door opened so that the robot could extract a part from the machine and then asks the machine to close that door once the part has been removed. 
         *
         * When these data items are used to describe a service associated with an {{term(interface)}}, they **MUST** have one of the following two `subType` elements: `REQUEST` or `RESPONSE`.  These **MUST** be specified to define whether the piece of equipment is functioning as the {{term(requester)}} or {{term(responder)}} for the service to be performed.  The {{term(requester)}} **MUST** specify the `REQUEST` `subType` for the data item and the {{term(responder)}} **MUST** specify a corresponding `RESPONSE` `subType` for the data item to enable the coordination between the two pieces of equipment.   
         *
         * These data items and their associated `subType` provide the basic structure for implementing the {{term(interaction model)}} for an {{term(interface)}} and are defined in the following sections.
         *
         * {{figure(Request State Machine)}} and {{figure(Response State Machine)}} show possible state transitions for a {{term(request)}} and {{term(response)}} respectively. The state machine diagrams provide the permissible values of the {{termplural(observation)}} for the {{block(DataItem)}} types listed in this section.
         *
         * ![Request State Machine](figures/Request%20State%20Machine.png "Request State Machine"){: width="0.8"}
         *
         * ![Response State Machine](figures/Response%20State%20Machine.png "Response State Machine"){: width="0.8"}
         */
    }
    package 'Data for Interface' {
        doc 
        /* Each {{term(interface)}} **MUST** provide the data associated with the specific {{term(interface)}} to implement the {{term(interaction model)}} and any additional data that may be needed by another piece of equipment to understand the operating states and conditions of the first piece of equipment as it applies to the {{term(interface)}}.
         *
         * Details on data items specific to the {{term(interaction model)}} for each type of {{term(interface)}} are provided in {{package(DataItem Types for Interface)}}.
         *
         * An implementer may choose any other data available from a piece of equipment to describe the operating states and other information needed to support an {{term(interface)}}.
         *
         * ### References for Interface
         *
         * Some of the data items needed to support a specific {{term(interface)}} may already be defined elsewhere in the {{term(MTConnectDevices Response Document)}} for a piece of equipment.  However, the implementer may not be able to directly associate this data with the {{term(interface)}} since the MTConnect Standard does not permit multiple occurrences of a piece of data to be configured in an {{term(MTConnectDevices Response Document)}}.  {{block(References)}} provides a mechanism for associating information defined elsewhere in the {{term(information model)}} for a piece of equipment with a specific {{term(interface)}}.  
         *
         * {{block(References)}} {{termplural(organize)}} {{block(Reference)}} elements.
         *
         * {{block(Reference)}} is a pointer to information that is associated with another entity defined elsewhere for a piece of equipment.
         *
         * {{block(References)}} is an economical syntax for providing interface specific information without directly duplicating the occurrence of the data. It provides a mechanism to include all necessary information required for interaction and deterministic information flow between pieces of equipment.
         *
         * For more information on the {{block(References)}} model, see {{package(Device Information Model)}}.*/
    }
    connection def {
        end observesInterfaceState : 'DataItem Types for Interface'::InterfaceState => target.observesInterfaceState;
        private end : Interface;
    }
    doc 
    /* In many manufacturing processes, multiple pieces of equipment must work together to perform a task.  The traditional method for coordinating the activities between individual pieces of equipment is to connect them using a series of wires to communicate equipment states and demands for action.  These interactions use simple binary ON/OFF signals to accomplished their intention.
     *
     * In the MTConnect Standard, {{termplural(interface)}} provides a means to replace this traditional method for interconnecting pieces of equipment with a structured {{term(interaction model)}} that provides a rich set of information used to coordinate the actions between pieces of equipment.  Implementers may utilize the information provided by this data model to (1) realize the interaction between pieces of equipment and (2) to extend the functionality of the equipment to improve the overall performance of the manufacturing process. 
     *
     * The {{term(interaction model)}} used to implement {{termplural(interface)}} provides a lightweight and efficient protocol, simplifies failure recovery scenarios, and defines a structure for implementing a Plug-And-Play relationship between pieces of equipment.  By standardizing the information exchange using this higher-level semantic information model, an implementer may more readily replace a piece of equipment in a manufacturing system with any other piece of equipment capable of providing similar {{term(interaction model)}} functions.
     *
     * Two primary functions are required to implement the {{term(interaction model)}} for an {{termplural(interface)}} and manage the flow of information between pieces of equipment.  Each piece of equipment needs to have the following:
     *
     * * An {{term(agent)}} which provides:
     *     
     *  - The data required to implement the {{term(interaction model)}}.
     *     
     *  - Any other data from a piece of equipment needed to implement the {{term(interface)}} – operating states of the equipment, position information, execution modes, process information, etc. 
     *  
     * * A client software application that enables the piece of equipment to acquire and interpret information from another piece of equipment. 
     *
     *
     * ## Interfaces Architecture
     *
     * MTConnect Standard is based on a communications method that provides no direct way for one piece of equipment to change the state of or cause an action to occur in another piece of equipment.  The {{term(interaction model)}} used to implement {{termplural(interface)}} is based on a {{term(publish and subscribe)}} type of communications as described in {{package(Fundamentals)}} and utilizes a {{term(request)}} and {{term(response)}} information exchange mechanism.  For {{termplural(interface)}}, pieces of equipment must perform both the publish ({{term(agent)}}) and subscribe (client) functions.  
     *
     *
     * > Note: The current definition of {{termplural(interface)}} addresses the interaction between two pieces of equipment.  Future releases of the MTConnect Standard may address the interaction between multiple (more than two) pieces of equipment.
     *
     * ![Data Flow Architecture for Interfaces](figures/Data%20Flow%20Architecture%20for%20Interfaces.png "Data Flow Architecture for Interfaces"){: width="0.8"}
     *
     * > Note: The data flow architecture illustrated in {{figure(Data Flow Architecture for Interfaces)}} was historically referred to in the MTConnect Standard as a read-read concept.
     *
     * In the implementation of the {{term(interaction model)}} for {{termplural(interface)}}, two pieces of equipment can exchange information in the following manner.  One piece of equipment indicates a {{term(request)}} for service by publishing a type of {{term(request)}} using a data item provided through an {{term(agent)}} as defined in {{package(DataItem Types for Interface)}}.  The client associated with the second piece of equipment, which is subscribing to data from the first machine, detects and interprets that {{term(request)}}.  If the second machine chooses to take any action to fulfill this {{term(request)}}, it can indicate its acceptance by publishing a {{term(response)}} using a data item provided through its {{term(agent)}}.  The client on the first piece of equipment continues to monitor information from the second piece of equipment until it detects an indication that the {{term(response)}} to the {{term(request)}} has been completed or has failed.
     *
     * An example of this type of interaction between pieces of equipment can be represented by a machine tool that wants the material to be loaded by a robot.  In this example, the machine tool is the {{term(requester)}}, and the robot is the {{term(responder)}}.  On the other hand, if the robot wants the machine tool to open a door, the robot becomes the {{term(requester)}} and the machine tool the {{term(responder)}}.
     *
     * ## Request and Response Information Exchange
     *
     * The {{block(DataItem)}} elements defined by the {{term(interaction model)}} each have a `REQUEST` and `RESPONSE` subtype.  These subtypes identify if the data item represents a {{term(request)}} or a {{term(response)}}.  Using these data items, a piece of equipment changes the state of its {{term(request)}} or {{term(response)}} to indicate information that can be read by the other piece of equipment.  To aid in understanding how the {{term(interaction model)}} functions, one can view this {{term(interaction model)}} as a simple state machine. 
     *
     * The interaction between two pieces of equipment can be described as follows.  When the {{term(requester)}} wants an activity to be performed, it transitions its {{term(request)}} state from a `READY` state to an `ACTIVE` state.  In turn, when the client on the {{term(responder)}} reads this information and interprets the {{term(request)}}, the {{term(responder)}} announces that it is performing the requested task by changing its response state to `ACTIVE`.  When the action is finished, the {{term(responder)}} changes its response state to `COMPLETE`.  This pattern of {{term(request)}} and {{term(response)}} provides the basis for the coordination of actions between pieces of equipment.  These actions are implemented using `EVENT` category data items.  (See {{package(DataItem Types for Interface)}} for details on the {{block(Event)}} type data items defined for {{termplural(interface)}}.)
     *
     * > Note: The implementation details of how the {{term(responder)}} piece of equipment reacts to the {{term(request)}} and then completes the requested task are up to the implementer.
     *
     * ![Request and Response Overview](figures/Request%20and%20Response%20Overview.png "Request and Response Overview"){: width="0.8"}
     *
     * The initial condition of both the {{term(request)}} and {{term(response)}} states on both pieces of equipment is `READY`.  The dotted lines indicate the on-going communications that occur to monitor the progress of the interactions between the pieces of equipment.
     *
     * The interaction between the pieces of equipment as illustrated in {{figure(Request and Response Overview)}} progresses through the sequence listed below.
     *
     * * The {{term(request)}} transitions from `READY` to `ACTIVE` signaling that a service is needed.
     *
     * * The {{term(response)}} detects the transition of the {{term(request)}}.
     *
     * * The {{term(response)}} transitions from `READY` to `ACTIVE` indicating that it is performing the action.
     *
     * * Once the action has been performed, the {{term(response)}} transitions to `COMPLETE`.
     *
     * * The {{term(request)}} detects the action is `COMPLETE`.
     *
     * * The {{term(request)}} transitions back to `READY` acknowledging that the service has been performed.
     *
     * * The {{term(response)}} detects the {{term(request)}} has returned to `READY`.
     *
     * * In recognition of this acknowledgement, the {{term(response)}} transitions back to `READY`.
     *
     * After the final action has been completed, both pieces of equipment are back in the `READY` state indicating that they are able to perform another action.*/
}
package 'Device Information Model' {
    package Components {
        abstract part def Component :> Glossary::'MTConnect Terms'::Component {
            doc /* logical or physical entity that provides a capability.*/
            comment /* Description*/
            attribute id [1] : Profile::DataTypes::ID {
                doc /* unique identifier for the {{block(Component)}}.*/
            }
            attribute name [0..1] : Profile::DataTypes::string {
                doc 
                /* name of the {{block(Component)}}.
                 *
                 * When provided, {{property(Component::name)}} **MUST** be unique for all child {{block(Component)}} entities of a parent {{block(Component)}}.*/
            }
            attribute nativeName [0..1] : Profile::DataTypes::string {
                doc /* common name associated with {{block(Component)}}.*/
            }
            attribute sampleInterval [0..1] : Profile::DataTypes::float {
                doc 
                /* interval in milliseconds between the completion of the reading of the data associated with the {{block(Component)}} until the beginning of the next sampling of that data.
                 *
                 * This information may be used by client software applications to understand how often information from a {{block(Component)}} is expected to be refreshed.
                 *
                 * The refresh rate for data from all child {{block(Component)}} entities will be the
                 * same as for the parent {{block(Component)}} element unless specifically overridden by another {{property(Component::sampleInterval)}} provided for the child {{block(Component)}}.*/
            }
            attribute sampleRate [0..1] : Profile::DataTypes::float {
                doc /* **DEPRECATED** in *MTConnect Version 1.2*. Replaced by {{property(Component::sampleInterval)}}.*/
            }
            attribute uuid [0..1] : Profile::DataTypes::UUID {
                doc /* universally unique identifier for the {{block(Component)}}.*/
            }
            part hasDescription [0..1] : Description;
            part hasComposition [0..*] : 'Device Information Model'::Compositions::Composition;
            part hasComponent [0..*] : Component;
            part hasConfiguration [0..1] : Configurations::Configuration;
            private ref part isComponentOf [0..1] : Component;
            part observes [0..*] : 'Device Information Model'::DataItems::DataItem;
            part madeObservation [0..*] : 'Observation Information Model'::Observation;
            part hasReference [0..*] : 'Device Information Model'::References::Reference;
            attribute coordinateSystemIdRef [0..1] : Profile::DataTypes::ID {
                doc /* specifies the {{block(CoordinateSystem)}} for this {{block(Component)}} and its children.*/
            }
            ref part hasComponentStream [0..1] : 'Observation Information Model'::ComponentStream;
            doc 
            /* {{block(Component)}} is an abstract entity and will be realized by specific {{block(Component)}} types for an {{block(MTConnectDevices)}} entity. See {{package(Component Types)}} for more details on the {{block(Component)}} types.
             *
             * {{block(Component)}} also provides structure for describing the {{term(lower level)}} entities associated with it.
             *
             * At least one of {{block(Component)}}, {{block(DataItem)}}, or {{block(Reference)}} entities **MUST** be provided for a {{block(Component)}}.
             *
             * ![Component Example](figures/Component%20Example.png "Component Example"){: width="0.8"}
             *
             * > Note: See {{lst(component-example)}} for the {{term(XML)}} representation of the same example.*/
        }
        part def Description {
            doc /* descriptive content.*/
            comment /* Description*/
            attribute manufacturer [0..1] : Profile::DataTypes::string {
                doc /* name of the manufacturer of the physical or logical part of a piece of equipment represented by this element.*/
            }
            attribute model [0..1] : Profile::DataTypes::string {
                doc /* model description of the physical part or logical function of a piece of equipment represented by this element.*/
            }
            attribute serialNumber [0..1] : Profile::DataTypes::string {
                doc /* serial number associated with a piece of equipment.*/
            }
            attribute station [0..1] : Profile::DataTypes::string {
                doc /* identifier where a manufacturing function takes place.*/
            }
            attribute value [0..1] : Profile::DataTypes::string {
                doc /* description of the element.*/
            }
            doc 
            /* > Note 1 to entry: See {{figure(Component Example)}} for an example.
             *
             * > Note 2 to entry: See {{lst(component-example)}} for the {{term(XML)}} representation of the same example.*/
        }
        package 'Component Types' {
            part def Actuator :> System {
                doc /* {{block(Component)}} composed of a physical apparatus that moves or controls a mechanism or system. */
                comment /* Description*/
                doc /* It takes energy usually provided by air, electric current, or liquid and converts the energy into some kind of motion.*/
            }
            abstract part def Auxiliary :> Component {
                doc /* abstract {{block(Component)}} composed of removable part(s) of a piece of equipment that provides supplementary or extended functionality.*/
                private ref part isAuxiliaryOf : Device;
            }
            abstract part def Axis :> Component {
                doc /* abstract {{block(Component)}} composed of a motion system that provides linear or rotational motion for a piece of equipment.*/
                comment /* Description*/
                private ref part isAxisOf : Device;
                doc 
                /* In robotics, the term *Axis* is synonymous with *Joint*. A *Joint* is the connection between two parts of the structure that move in relation to each other.
                 *
                 * {{block(Linear)}} and {{block(Rotary)}} components **MUST** have {{property(Component::name)}} that **MUST** follow the conventions described below. Use the {{property(Component::nativeName)}} for the manufacturer's name of the axis if it differs from the assigned {{property(Component::name)}}.
                 *
                 * MTConnect has two high-level classes for automation equipment as follows: (1) Equipment that controls cartesian coordinate axes and (2) Equipment that controls articulated axes. There are ambiguous cases where some machines exhibit both characteristics; when this occurs, the primary control system's configuration determines the classification.
                 *
                 * Examples of cartesian coordinate equipment are CNC Machine Tools, Coordinate measurement machines, as specified in ISO 841, and 3D Printers. Examples of articulated automation equipment are Robotic systems as specified in ISO 8373.
                 *
                 * The following sections define the designation of names for the axes and additional guidance when selecting the correct scheme to use for a given piece of equipment.
                 *
                 * #### Cartesian Coordinate Naming Conventions
                 *
                 * A Three-Dimensional Cartesian Coordinate control system organizes its axes orthogonally relative to a machine coordinate system where the manufacturer of the equipment specifies the origin. 
                 *
                 * {{block(Axes)}} {{property(Component::name)}} **SHOULD** comply with ISO 841, if possible.
                 *
                 * ##### Linear Motion
                 *
                 * A piece of equipment **MUST** represent prismatic motion using a {{block(Linear)}} axis and assign its {{property(Component::name)}} using the designations `X`, `Y`, and `Z`. A {{block(Linear)}} axis {{property(Component::name)}} **MUST** append a monotonically increasing suffix when there are more than one parallel axes; for example, `X2`, `X3`, and `X4`. 
                 *
                 * ##### Rotary Motion
                 *
                 * MTConnect **MUST** assign the {{property(Component::name)}} to {{block(Rotary)}} axes exhibiting rotary motion using `A`, `B`, and `C`. A {{block(Rotary)}} axis {{property(Component::name)}} **MUST** append a monotonically increasing suffix when more than one {{block(Rotary)}} axis rotates around the same {{block(Linear)}} axis; for example, `A2`, `A3`, and `A4`. 
                 *
                 * #### Articulated Machine Control Systems
                 *
                 * An articulated control system's axes represent the connecting linkages between two adjacent rigid members of an assembly. The {{block(Linear)}} axis represents prismatic motion, and the {{block(Rotary)}} axis represents the rotational motion of the two related members. The control organizes the axes in a kinematic chain from the mounting surface (base) to the end-effector or tooling.
                 *
                 * #### Articulated Machine Axis Names
                 *
                 * The axes of articulated machines represent forward kinematic relationships between mechanical linkages. Each axis is a connection between linkages, also referred to as joints, and **MUST** be named using a `J` followed by a monotonically increasing number; for example, `J1`, `J2`, `J3`.  The numbering starts at the base axis connected or closest to the mounting surface, `J1`, incrementing to the mechanical interface, `Jn`, where `n` is the number of the last axis. The chain forms a parent-child relationship with the parent being the axis closest to the base.
                 *
                 * A machine having an axis with more than one child **MUST** number each branch using its numeric designation followed by a branch number and a monotonically increasing number. For example, if `J2` has two children, the first child branch **MUST** be named `J2.1.1` and the second child branch `J2.2.1`. A child of the first branch **MUST** be named `J2.1.2`, incrementing to `J2.1.n`, where `J2.1.n` is the number of the last axis in that branch.*/
            }
            part def BarFeeder :> Loader {
                doc /* {{block(Loader)}} that delivers bar stock to a piece of equipment.*/
            }
            part def Controller :> System {
                doc /* {{block(System)}} that provides regulation or management of a system or component. {{cite(ISO 16484-5:2017)}}*/
                comment /* Description*/
                part hasPath [0..*] : Path;
                private ref part isControllerOf [1] : Device;
                part observesEmergencyStop [0..1] : 'Observation Information Model'::'Observation Types'::'Event Types'::EmergencyStop;
                part observesSystemCondition [0..1] : 'Observation Information Model'::'Observation Types'::'Condition Types'::System;
                part observesControllerMode [0..1] : 'Observation Information Model'::'Observation Types'::'Event Types'::ControllerMode;
                part observesCommunicationsCondition [0..1] : 'Observation Information Model'::'Observation Types'::'Condition Types'::Communications;
                part observesLogicProgramCondition [0..1] : 'Observation Information Model'::'Observation Types'::'Condition Types'::LogicProgram;
                doc 
                /* Typical types of controllers for a piece of equipment include CNC (Computer Numerical Control), PAC (Programmable Automation Control), IPC (Industrialized Computer), or IC (Imbedded Computer).
                 *
                 * > Note: In {{term(XML)}} representation, {{block(Controller)}} is a {{term(top level)}} element.*/
            }
            part def Coolant :> System {
                doc /* {{block(System)}} that provides distribution and management of fluids that remove heat from a piece of equipment.*/
                part observesConcentration [0..1] : 'Observation Information Model'::'Observation Types'::'Sample Types'::Concentration;
            }
            part def Deposition :> Auxiliary {
                doc /* {{block(Auxiliary)}} that manages the addition of material or state change of material being performed in an additive manufacturing process.*/
                comment /* Description*/
                doc /* For example, this could describe the portion of a piece of equipment that manages a material extrusion process or a vat polymerization process.*/
            }
            part def Dielectric :> System {
                doc /* {{block(System)}} that manages a chemical mixture used in a manufacturing process being performed at that piece of equipment.*/
                comment /* Description*/
                doc /* For example, this could describe the dielectric system for an EDM process or the chemical bath used in a plating process.*/
            }
            part def Door :> Component {
                doc /* {{block(Component)}} composed of a mechanical mechanism or closure that can cover a physical access portal into a piece of equipment allowing or restricting access to other parts of the equipment.*/
                comment /* Description*/
                part observesDoorState [1] : 'Observation Information Model'::'Observation Types'::'Event Types'::DoorState;
                doc 
                /* The closure can be opened or closed to allow or restrict access to other parts of the equipment.
                 *
                 * {{block(Door)}} **MUST** have {{block(DoorState)}} data item to indicate if the door is `OPEN`, `CLOSED`, or `UNLATCHED`. A {{block(Component)}} **MAY** contain multiple {{block(Door)}} entities.*/
            }
            part def Electric :> System {
                doc /* {{block(System)}} composed of the main power supply for the piece of equipment that provides distribution of that power throughout the equipment.*/
                comment /* Description*/
                part observesWattage [0..1] : 'Observation Information Model'::'Observation Types'::'Sample Types'::Wattage;
                doc /* The electric system will provide all the data with regard to electric current, voltage, frequency, etc. that applies to the piece of equipment as a functional unit. Data regarding electric power that is specific to a {{block(Component)}} will be reported for that specific {{block(Component)}}.*/
            }
            part def Enclosure :> System {
                doc /* {{block(System)}} composed of a structure that is used to contain or isolate a piece of equipment or area.*/
                comment /* Description*/
                doc /* {{block(Enclosure)}} may provide information regarding access to the internal components of a piece of equipment or the conditions within the enclosure. For example, {{block(Door)}} may be defined as a {{term(lower level)}} {{block(Component)}} or {{block(Composition)}} entity of the {{block(Enclosure)}}.*/
            }
            part def EndEffector :> System {
                doc /* {{block(System)}} composed of functions that form the last link segment of a piece of equipment.*/
                comment /* Description*/
                doc /* It is the part of a piece of equipment that interacts with the manufacturing process.*/
            }
            part def Environmental :> Component {
                doc 
                /* {{block(Component)}} that observes the surroundings of another {{block(Component)}}.
                 *
                 * > Note: {{block(Environmental)}} **SHOULD** be organized by {{block(Auxillaries)}}, {{block(Systems)}} or {{block(Parts)}} depending on the relationship to the {{block(Component)}}.*/
            }
            part def Feeder :> System {
                doc /* {{block(System)}} that manages the delivery of materials within a piece of equipment.*/
                comment /* Description*/
                doc /* For example, this could describe the wire delivery system for an EDM or welding process; conveying system or pump and valve system distributing material to a blending station; or a fuel delivery system feeding a furnace.*/
            }
            part def Hydraulic :> Actuator {
                doc /* {{block(System)}} that provides movement and distribution of pressurized liquid throughout the piece of equipment.*/
                part observesPressure [0..1] : 'Observation Information Model'::'Observation Types'::'Sample Types'::Pressure;
            }
            part def Linear :> Axis {
                doc /* {{block(Component Types::Axis)}} that provides prismatic motion along a fixed axis.*/
                part observesLoad [0..1] : 'Observation Information Model'::'Observation Types'::'Sample Types'::Load;
                part observesTemperature [0..1] : 'Observation Information Model'::'Observation Types'::'Sample Types'::Temperature;
                part observesAxisFeedrateActual [0..1] : 'Observation Information Model'::'Observation Types'::'Sample Types'::'AxisFeedrate.Actual';
            }
            part def Loader :> Auxiliary {
                doc /* {{block(Auxiliary)}} that provides movement and distribution of materials, parts, tooling, and other items to or from a piece of equipment.*/
            }
            part def Lubrication :> System {
                doc /* {{block(System)}} that provides distribution and management of fluids used to lubricate portions of the piece of equipment.*/
            }
            part def Material :> Resource {
                doc /* {{block(Resource)}} composed of material that is consumed or used by the piece of equipment for production of parts, materials, or other types of goods.*/
            }
            part def Path :> Component {
                doc /* {{block(Component)}} that organizes an independent operation or function within a {{block(Controller)}}.*/
                comment /* Description*/
                part observesExecution [0..1] : 'Observation Information Model'::'Observation Types'::'Event Types'::Execution;
                part observesProgram [0..1] : 'Observation Information Model'::'Observation Types'::'Event Types'::Program;
                part observesPathFeedrateOverrideProgrammed [0..1] : 'Observation Information Model'::'Observation Types'::'Event Types'::'PathFeedrateOverride.Programmed';
                part observesPathFeedrateOverrideRapid [0..1] : 'Observation Information Model'::'Observation Types'::'Event Types'::'PathFeedrateOverride.Rapid';
                part observesRotaryVelocityOverride [0..1] : 'Observation Information Model'::'Observation Types'::'Event Types'::RotaryVelocityOverride;
                part observesPathFeedrate [0..1] : 'Observation Information Model'::'Observation Types'::'Sample Types'::PathFeedrate;
                part observesPartCount [0..1] : 'Observation Information Model'::'Observation Types'::'Event Types'::PartCount;
                doc 
                /* For many types of equipment, {{block(Path)}} organizes a set of {{block(Axes)}}, one or more Program elements, and the data associated with the motion of a control point as it moves through space. However, it **MAY** also represent any independent function within a {{block(Controller)}} that has unique data associated with that function.
                 *  
                 * {{block(Path)}} **SHOULD** provide an {{block(Execution)}} data item to define the operational state of the {{block(Controller)}} of the piece of equipment.
                 *
                 * If the {{block(Controller)}} is capable of performing more than one independent operation or function simultaneously, a separate {{block(Path)}} **MUST** be used to organize the data associated with each independent operation or function.*/
            }
            part def Personnel :> Resource {
                doc /* {{block(Resource)}} composed of an individual or individuals who either control, support, or otherwise interface with a piece of equipment.
                 */
                part observesUserOperator [0..1] : 'Observation Information Model'::'Observation Types'::'Event Types'::'User.Operator';
                part observesUserMaintenance [0..1] : 'Observation Information Model'::'Observation Types'::'Event Types'::'User.Maintenance';
            }
            part def Pneumatic :> Actuator {
                doc /* {{block(System)}} that uses compressed gasses to actuate components or do work within the piece of equipment.*/
                comment /* Description*/
                part observesPressure [0..1] : 'Observation Information Model'::'Observation Types'::'Sample Types'::Pressure;
                doc /* > Note: Actuation is usually performed using a cylinder.*/
            }
            part def Power :> Component {
                doc /* {{block(Power)}} was **DEPRECATED** in *MTConnect Version 1.1* and was replaced by {{block(Availability)}} data item type.*/
            }
            part def ProcessPower :> System {
                doc /* {{block(System)}} composed of a power source associated with a piece of equipment that supplies energy to the manufacturing process separate from the {{block(Electric)}} system.*/
                comment /* Description*/
                doc /* For example, this could be the power source for an EDM machining process, an electroplating line, or a welding system.*/
            }
            part def Protective :> System {
                doc /* {{block(System)}} that provides functions used to detect or prevent harm or damage to equipment or personnel.*/
                comment /* Description*/
                doc /* {{block(Protective)}} does not include the information relating to the {{block(Enclosure)}}.*/
            }
            abstract part def Resource :> Component {
                doc /* abstract {{block(Component)}} composed of material or personnel involved in a manufacturing process.*/
                private ref part isResourceOf : Device;
            }
            part def Rotary :> Axis {
                doc /* {{block(Component Types::Axis)}} that provides rotation about a fixed axis.*/
                part observesLoad [0..1] : 'Observation Information Model'::'Observation Types'::'Sample Types'::Load;
                part observesTemperature [0..1] : 'Observation Information Model'::'Observation Types'::'Sample Types'::Temperature;
                part observesRotaryVelocity [0..1] : 'Observation Information Model'::'Observation Types'::'Sample Types'::RotaryVelocity;
                part observesAxisFeedrate [0..1] : 'Observation Information Model'::'Observation Types'::'Sample Types'::AxisFeedrate;
            }
            part def Sensor :> Component {
                doc /* {{block(Component)}} that responds to a physical stimulus and transmits a resulting impulse or value from a sensing unit.*/
                comment /* Description*/
                doc 
                /* If modeling individual sensors, then sensor should be associated with the {{block(Component)}} that the measured value is most closely associated.
                 *
                 * When modeled as an {{block(Auxiliary)}}, sensor **SHOULD** represent an integrated {{term(sensor unit)}} system that provides signal processing, conversion, and communications. A {{term(sensor unit)}} may have multiple {{termplural(sensing element)}}.
                 *
                 * See {{block(SensorConfiguration)}} for more details on the use and configuration of a {{block(Sensor)}}.*/
            }
            part def Stock :> Material {
                doc /* {{block(Material)}} that is used in a manufacturing process and to which work is applied in a machine or piece of equipment to produce parts.*/
                comment /* Description*/
                part observesMaterial [0..1] : 'Observation Information Model'::'Observation Types'::'Event Types'::Material;
                part observesLengthRemaining [0..1] : 'Observation Information Model'::'Observation Types'::'Sample Types'::'Length.Remaining';
                part observesLengthStandard [0..1] : 'Observation Information Model'::'Observation Types'::'Sample Types'::'Length.Standard';
                doc /* {{block(Stock)}} may be either a continuous piece of material from which multiple parts may be produced or it may be a discrete piece of material that will be made into a part or a set of parts.*/
            }
            abstract part def System :> Component {
                doc /* abstract {{block(Component)}} that is permanently integrated into the piece of equipment.*/
                private ref part isSystemOf : Device;
            }
            part def ToolingDelivery :> Auxiliary {
                doc /* {{block(Auxiliary)}} that manages, positions, stores, and delivers tooling within a piece of equipment.
                 */
            }
            part def WasteDisposal :> Auxiliary {
                doc /* {{block(Auxiliary)}} that removes manufacturing byproducts from a piece of equipment.*/
            }
            part def Structure :> Component {
                doc /* {{block(Component)}} composed of part(s) comprising the rigid bodies of the piece of equipment.*/
                private ref part isStructureOf : Device;
            }
            part def Link :> Structure {
                doc /* {{block(Structure)}} that provides a connection between {{block(Component)}} entities.*/
            }
            connection def {
                private end pneumatic : Pneumatic;
                private end : System;
            }
            connection def {
                private end electric : Electric;
                private end : System;
            }
            connection def {
                private end enclosure : Enclosure;
                private end : System;
            }
            connection def {
                private end fan : Fan;
                private end : Enclosure;
            }
            connection def {
                private end workEnvelope : WorkEnvelope;
                private end : System;
            }
            part def GangToolBar :> ToolingDelivery {
                doc /* {{block(ToolingDelivery)}} composed of a tool mounting mechanism that holds any number of tools. */
                comment /* Description*/
                doc /* Tools are located in {{block(Station)}} entities. Tools are positioned for use in the manufacturing process by linearly positioning the {{block(GangToolBar)}}.*/
            }
            part def Heating :> System {
                doc /* {{block(System)}} that delivers controlled amounts of heat to achieve a target temperature at a specified heating rate.*/
                comment /* Description*/
                doc /* > Note: As an example, Energy Delivery Method can be either through Electric heaters or Gas burners.*/
            }
            part def AutomaticToolChanger :> ToolingDelivery {
                doc /* {{block(ToolingDelivery)}} composed of a tool delivery mechanism that moves tools between a {{block(ToolMagazine)}} and a {{term(spindle)}} a {{block(Turret)}}.*/
                comment /* Description*/
                doc /* {{block(AutomaticToolChanger)}} may also transfer tools between a location outside of a piece of equipment and a {{block(ToolMagazine)}} or {{block(Turret)}}.*/
            }
            abstract part def Process :> Component {
                doc /* abstract {{block(Component)}} composed of a manufacturing process being executed on a piece of equipment.*/
                private ref part isExecutedOn : Device;
            }
            part def ToolMagazine :> ToolingDelivery {
                doc /* {{block(ToolingDelivery)}} composed of a tool storage mechanism that holds any number of tools. 
                 */
                comment /* Description*/
                doc /* Tools are located in {{block(Pot)}}s. {{block(Pot)}}s are moved into position to transfer tools into or out of the {{block(ToolMagazine)}} by an {{block(AutomaticToolChanger)}}.*/
            }
            part def PartOccurrence :> Part {
                doc /* {{block(Part)}} that exists at a specific place and time, such as a specific instance of a bracket at a specific timestamp.*/
                comment /* Description*/
                comment /* Example*/
                part observesPartId [0..1] : 'Observation Information Model'::'Observation Types'::'Event Types'::PartId;
                part observesPartUniqueId [0..1] : 'Observation Information Model'::'Observation Types'::'Event Types'::PartUniqueId;
                part observesPartGroupId [0..1] : 'Observation Information Model'::'Observation Types'::'Event Types'::PartGroupId;
                part observesPartKindId [0..1] : 'Observation Information Model'::'Observation Types'::'Event Types'::PartKindId;
                part observesPartCount [0..1] : 'Observation Information Model'::'Observation Types'::'Event Types'::PartCount;
                part observesPartStatus [0..1] : 'Observation Information Model'::'Observation Types'::'Event Types'::PartStatus;
                part observesProcessOccurrenceId [0..1] : 'Observation Information Model'::'Observation Types'::'Event Types'::ProcessOccurrenceId;
                part observesProcessTime [0..1] : 'Observation Information Model'::'Observation Types'::'Event Types'::ProcessTime;
                part observesUser [0..1] : 'Observation Information Model'::'Observation Types'::'Event Types'::User;
                doc /* {{block(PartId)}} **MUST** be defined for {{block(PartOccurrence)}}.*/
                doc 
                /*
                 * ~~~~xml
                 * <Parts id="partOccSet">
                 *    <Components>
                 * 	   <PartOccurrence id="partOccur">
                 * 		 <DataItems>
                 * 		   <DataItem id="partSet" category="EVENT" representation="TABLE" type ="COMPONENT_DATA">
                 * 			  <Definition>
                 * 				 <EntryDefinitions>
                 * 					  <EntryDefinition keyType="PART_UNIQUE_ID"/>
                 * 				 </EntryDefinitions>
                 * 				 <CellDefinitions>
                 * 					<CellDefinition key="partNumber" type="PART_KIND_ID" subType="PART_NUMBER"/>
                 * 					<CellDefinition key="batchId" type="PART_GROUP_ID" subType="BATCH"/>
                 * 					<CellDefinition key="quantity" type="PART_COUNT" subType="TARGET"/>
                 * 					<CellDefinition key="actualCompleteTime" type="PROCESS_TIME" subType="COMPLETE"/>
                 * 					<CellDefinition key="partState" type="PROCESS_STATE"/>
                 * 				</CellDefinitions>
                 * 			  </Definition>
                 * 			</DataItem>
                 * 		 </DataItems>
                 * 	   </PartOccurrence>
                 * 	</Components>
                 * </Parts>
                 * ~~~~
                 * {: caption="XML Device Model Example for PartOccurrence and ComponentData"}
                 *
                 *
                 * ~~~~xml
                 * <?xml version="1.0" encoding="UTF-8"?>
                 * <?xml-stylesheet type="text/xsl" href="/styles/Streams.xsl"?>
                 * <MTConnectStreams>
                 *   <Streams>
                 *     <DeviceStream name="VMC-3Axis" uuid="test_27MAY">
                 *       <ComponentStream component="PartOccurrence" name="partSet" componentId="partOccur">
                 *         <Events>
                 *           <ComponentDataTable dataItemId="partSet" timestamp="2020-10-28T19:45:43.070010Z" sequence="95" count="2">
                 *             <Entry key="part1">
                 *               <Cell key="actualStartTime">2009-06-15T00:00:00.000000</Cell>
                 *               <Cell key="partId">part1</Cell>
                 *               <Cell key="partName">SomeName</Cell>
                 *               <Cell key="uniqueID">abc-123</Cell>
                 *             </Entry>
                 *             <Entry key="part2">
                 *               <Cell key="actualStartTime">2009-06-15T00:00:00.007925</Cell>
                 *               <Cell key="partId">part2</Cell>
                 *               <Cell key="partName">AnotherName</Cell>
                 *               <Cell key="uniqueID">def-123</Cell>
                 *             </Entry>
                 *           </ComponentDataTable>
                 *         </Events>
                 *       </ComponentStream>
                 *     </DeviceStream>
                 *   </Streams>
                 * </MTConnectStreams>
                 * ~~~~
                 * {: caption="XML Streams Response Example for PartOccurrence and ComponentData"}*/
            }
            part def Adapter :> Component {
                doc /* {{block(Component)}} that provides information about the data source for an {{term(MTConnect Agent)}}.*/
                comment /* Description*/
                private ref part isAdapterOf : Device;
                doc /* It **MAY** contain connectivity state of the data source and additional telemetry about the data source and source-specific information.*/
            }
            part def ToolRack :> ToolingDelivery {
                doc /* {{block(ToolingDelivery)}} composed of a linear or matrixed tool storage mechanism that holds any number of tools.*/
                comment /* Description*/
                doc /* Tools are located in {{block(Station)}} entities.*/
            }
            part def Turret :> ToolingDelivery {
                doc /* {{block(ToolingDelivery)}} composed of a tool mounting mechanism that holds any number of tools.*/
                comment /* Description*/
                doc /* Tools are positioned for use in the manufacturing process by rotating the {{block(Turret)}}.*/
            }
            connection def Path {
                end hasPath : Path => target.hasPath;
                private end : Controller;
            }
            part def Vacuum :> System {
                doc /* {{block(System)}} that evacuates gases and liquids from an enclosed and sealed space to a controlled negative pressure or a molecular density below the prevailing atmospheric level.*/
            }
            part def Cooling :> System {
                doc /* {{block(System)}} that extracts controlled amounts of heat to achieve a target temperature at a specified cooling rate.*/
                comment /* Description*/
                doc /* > Note: As an example, Energy Extraction Method can be via cooling water pipes running through the chamber.*/
            }
            part def ProcessOccurrence :> Process {
                doc /* {{block(Process)}} that takes place at a specific place and time, such as a specific instance of part-milling occurring at a specific timestamp.*/
                comment /* Description*/
                part observesProcessOccurrenceId [0..1] : 'Observation Information Model'::'Observation Types'::'Event Types'::ProcessOccurrenceId;
                part observesProcessAggregateId [0..1] : 'Observation Information Model'::'Observation Types'::'Event Types'::ProcessAggregateId;
                part observesProcessTime [0..1] : 'Observation Information Model'::'Observation Types'::'Event Types'::ProcessTime;
                part observesProcessKindId [0..1] : 'Observation Information Model'::'Observation Types'::'Event Types'::ProcessKindId;
                part observesUser [0..1] : 'Observation Information Model'::'Observation Types'::'Event Types'::User;
                part observesProgram [0..1] : 'Observation Information Model'::'Observation Types'::'Event Types'::Program;
                part observesPartUniqueId [0..1] : 'Observation Information Model'::'Observation Types'::'Event Types'::PartUniqueId;
                doc /* {{block(ProcessOccurrenceId)}} **MUST** be defined for {{block(ProcessOccurrence)}}.*/
            }
            part def Pressure :> System {
                doc /* {{block(System)}} that delivers compressed gas or fluid and controls the pressure and rate of pressure change to a desired target set-point.*/
                comment /* Description*/
                doc /* > Note: For example, Delivery Method can be a Compressed Air or N2 tank that is piped via an inlet valve to the chamber.*/
            }
            connection def {
                end observesProcessOccurrenceId : 'Observation Information Model'::'Observation Types'::'Event Types'::ProcessOccurrenceId => target.observesProcessOccurrenceId;
                private end : ProcessOccurrence;
            }
            connection def {
                end observesProcessAggregateId : 'Observation Information Model'::'Observation Types'::'Event Types'::ProcessAggregateId => target.observesProcessAggregateId;
                private end : ProcessOccurrence;
            }
            connection def {
                end observesProcessTime : 'Observation Information Model'::'Observation Types'::'Event Types'::ProcessTime => target.observesProcessTime;
                private end : ProcessOccurrence;
            }
            connection def {
                end observesLockState : 'Observation Information Model'::'Observation Types'::'Event Types'::LockState => target.observesLockState;
                private end : Lock;
            }
            abstract part def Part :> Component {
                doc /* abstract {{block(Component)}} composed of a {{term(part)}} being processed by a piece of equipment.*/
                private ref part isWorkedOn : Device;
            }
            part def Lock :> Component {
                doc /* {{block(Component)}} that physically prohibits a {{block(Device)}} or {{block(Component)}} from opening or operating.*/
                part observesLockState [0..1] : 'Observation Information Model'::'Observation Types'::'Event Types'::LockState;
            }
            package 'Component Organizer Types' {
                connection def Structures :> Component {
                    doc /* {{block(Component)}} that {{termplural(organize)}} {{block(Structure)}} types. */
                    private end device : Device => structure.'Device Information Model'::Components::'Component Types'::Structure::isStructureOf;
                    private end structure : Structure => device.hasStructure;
                }
                connection def Interfaces :> Component {
                    doc /* {{block(Component)}} that {{termplural(organize)}} {{block(Interface)}} types. */
                    private end device : Device => 'interface'.'Interface Interaction Model'::Interface::isInterfaceOf;
                    private end 'interface' : 'Interface Interaction Model'::Interface => device.hasInterface;
                }
                connection def Auxiliaries :> Component {
                    doc /* {{block(Component)}} that {{termplural(organize)}} {{block(Auxiliary)}} types. */
                    private end device : Device => auxiliary.'Device Information Model'::Components::'Component Types'::Auxiliary::isAuxiliaryOf;
                    private end auxiliary : Auxiliary => device.hasAuxiliary;
                }
                connection def Systems :> Component {
                    doc /* {{block(Component)}} that {{termplural(organize)}} {{block(System)}} types. */
                    private end device : Device => system.'Device Information Model'::Components::'Component Types'::System::isSystemOf;
                    private end system : System => device.hasSystem;
                }
                connection def Adapters :> Component {
                    doc /* {{block(Component)}} that {{termplural(organize)}} {{block(Adapter)}} types. */
                    private end device : Device => adapter.'Device Information Model'::Components::'Component Types'::Adapter::isAdapterOf;
                    private end adapter : Adapter => device.hasAdapter;
                }
                connection def Resources :> Component {
                    doc /* {{block(Component)}} that {{termplural(organize)}} {{block(Resource)}} types. */
                    private end device : Device => resource.'Device Information Model'::Components::'Component Types'::Resource::isResourceOf;
                    private end resource : Resource => device.hasResource;
                    private part hasMaterial [0..*] : Material;
                }
                connection def Axes :> Component {
                    doc /* {{block(Component)}} that {{termplural(organize)}} {{block(Component Types::Axis)}} types. */
                    private end device : Device => axis.'Device Information Model'::Components::'Component Types'::Axis::isAxisOf;
                    private end axis : Axis => device.hasAxis;
                }
                connection def Processes :> Component {
                    doc /* {{block(Component)}} that {{termplural(organize)}} {{block(Process)}} types. */
                    private end device : Device => process.'Device Information Model'::Components::'Component Types'::Process::isExecutedOn;
                    private end process : Process => device.'Device Information Model'::Device::hasProcess;
                }
                connection def Parts :> Component {
                    doc /* {{block(Component)}} that {{termplural(organize)}} {{block(Part)}} types.*/
                    private end device : Device => 'part'.'Device Information Model'::Components::'Component Types'::Part::isWorkedOn;
                    private end 'part' : Part => device.'Device Information Model'::Device::hasPart;
                }
                connection def Materials :> Resources {
                    doc /* {{block(Resources)}} that {{termplural(organize)}} {{block(Material)}} types.*/
                    private end material : Material => resources.'Device Information Model'::Components::'Component Types'::'Component Organizer Types'::Resources::hasMaterial;
                    end resources : Resources;
                }
                connection def Controllers {
                    doc /* {{block(Component)}} that {{termplural(organize)}} {{block(Controller)}} entities.*/
                    end device : Device => controller.'Device Information Model'::Components::'Component Types'::Controller::isControllerOf;
                    end controller : Controller => device.hasController;
                }
                doc /* This section provides semantic information for the types of {{block(Component)}} that are used to {{term(organize)}} other {{block(Component)}} types. */
            }
            part def Spindle :> Axis {
                doc 
                /* {{block(Component)}} that provides an axis of rotation for the purpose of rapidly rotating a part or a tool to provide sufficient surface speed for cutting operations.
                 *
                 * {{block(Spindle)}} was **DEPRECATED** in *MTConnect Version 1.1* and was replaced by {{block(RotaryMode)}}.*/
            }
            part def Thermostat :> Sensor {
                doc 
                /* {{block(Component)}} composed of a sensor or an instrument that measures temperature.
                 *
                 * {{block(Thermostat)}} was **DEPRECATED** in *MTConnect Version 1.2* and was replaced by {{block(Temperature)}}.*/
            }
            part def Vibration :> Sensor {
                doc 
                /* {{block(Component)}} composed of a sensor or an instrument that measures the amount and/or frequency of vibration within a system.
                 *
                 * {{block(Vibration)}} was **DEPRECATED** in *MTConnect Version 1.2* and was replaced by {{block(Displacement)}}, {{block(Frequency)}} etc.*/
            }
            part def Chuck :> Component {
                doc /* leaf {{block(Component)}} composed of a mechanism that holds a part or stock material in place.*/
            }
            connection def {
                end observesDoorState : 'Observation Information Model'::'Observation Types'::'Event Types'::DoorState => target.observesDoorState;
                private end : Door;
            }
            connection def {
                end observesExecution : 'Observation Information Model'::'Observation Types'::'Event Types'::Execution => target.observesExecution;
                private end : Path;
            }
            connection def {
                end observesProcessKindId : 'Observation Information Model'::'Observation Types'::'Event Types'::ProcessKindId => target.observesProcessKindId;
                private end : ProcessOccurrence;
            }
            connection def {
                end observesUser : 'Observation Information Model'::'Observation Types'::'Event Types'::User => target.observesUser;
                private end : ProcessOccurrence;
            }
            connection def {
                end observesProgram : 'Observation Information Model'::'Observation Types'::'Event Types'::Program => target.observesProgram;
                private end : ProcessOccurrence;
            }
            connection def {
                end observesPartUniqueId : 'Observation Information Model'::'Observation Types'::'Event Types'::PartUniqueId => target.observesPartUniqueId;
                private end : ProcessOccurrence;
            }
            connection def {
                end observesPartId : 'Observation Information Model'::'Observation Types'::'Event Types'::PartId => target.observesPartId;
                private end : PartOccurrence;
            }
            connection def {
                end observesPartUniqueId : 'Observation Information Model'::'Observation Types'::'Event Types'::PartUniqueId => target.observesPartUniqueId;
                private end : PartOccurrence;
            }
            connection def {
                end observesPartGroupId : 'Observation Information Model'::'Observation Types'::'Event Types'::PartGroupId => target.observesPartGroupId;
                private end : PartOccurrence;
            }
            connection def {
                end observesPartKindId : 'Observation Information Model'::'Observation Types'::'Event Types'::PartKindId => target.observesPartKindId;
                private end : PartOccurrence;
            }
            connection def {
                end observesPartCount : 'Observation Information Model'::'Observation Types'::'Event Types'::PartCount => target.observesPartCount;
                private end : PartOccurrence;
            }
            connection def {
                end observesPartStatus : 'Observation Information Model'::'Observation Types'::'Event Types'::PartStatus => target.observesPartStatus;
                private end : PartOccurrence;
            }
            connection def {
                end observesProcessOccurrenceId : 'Observation Information Model'::'Observation Types'::'Event Types'::ProcessOccurrenceId => target.observesProcessOccurrenceId;
                private end : PartOccurrence;
            }
            connection def {
                end observesProcessTime : 'Observation Information Model'::'Observation Types'::'Event Types'::ProcessTime => target.observesProcessTime;
                private end : PartOccurrence;
            }
            connection def {
                end observesUser : 'Observation Information Model'::'Observation Types'::'Event Types'::User => target.observesUser;
                private end : PartOccurrence;
            }
            part def Fan :> Component {
                doc /* leaf {{block(Component)}} that produces a current of air.*/
                part hasComposition [0] :>> hasComposition : 'Device Information Model'::Compositions::Composition;
                part hasComponent [0] :>> hasComponent : Component;
            }
            part def Spreader :> Component {
                doc /* leaf {{block(Component)}} that flattens or spreading materials.*/
                part hasComposition [0] :>> hasComposition : 'Device Information Model'::Compositions::Composition;
                part hasComponent [0] :>> hasComponent : Component;
            }
            part def Pulley :> Component {
                doc /* leaf {{block(Component)}} composed of a mechanism or wheel that turns in a frame or block and serves to change the direction of or to transmit force.*/
                part hasComposition [0] :>> hasComposition : 'Device Information Model'::Compositions::Composition;
                part hasComponent [0] :>> hasComponent : Component;
            }
            part def TransferPot :> Component {
                doc /* leaf {{block(Component)}} that is a {{block(Pot)}} for a tool that is awaiting transfer from a {{block(ToolMagazine)}} to {{term(spindle)}} or {{block(Turret)}}.*/
                part hasComposition [0] :>> hasComposition : 'Device Information Model'::Compositions::Composition;
                part hasComponent [0] :>> hasComponent : Component;
            }
            part def PowerSupply :> Component {
                doc /* leaf {{block(Component)}} that provides power to electric mechanisms.*/
                part hasComposition [0] :>> hasComposition : 'Device Information Model'::Compositions::Composition;
                part hasComponent [0] :>> hasComponent : Component;
            }
            part def Drain :> Component {
                doc /* leaf {{block(Component)}} that allows material to flow for the purpose of drainage from, for example, a vessel or tank.*/
                part hasComposition [0] :>> hasComposition : 'Device Information Model'::Compositions::Composition;
                part hasComponent [0] :>> hasComponent : Component;
            }
            part def Ballscrew :> Component {
                doc /* leaf {{block(Component)}} composed of a mechanical structure that transforms rotary motion into linear motion.*/
                part hasComposition [0] :>> hasComposition : 'Device Information Model'::Compositions::Composition;
                part hasComponent [0] :>> hasComponent : Component;
            }
            part def Compressor :> Component {
                doc /* leaf {{block(Component)}} composed of a pump or other mechanism that reduces volume and increases pressure of gases in order to condense the gases to drive pneumatically powered pieces of equipment.*/
                part hasComposition [0] :>> hasComposition : 'Device Information Model'::Compositions::Composition;
                part hasComponent [0] :>> hasComponent : Component;
            }
            part def Chute :> Component {
                doc /* leaf {{block(Component)}} composed of an inclined channel that conveys material.*/
                part hasComposition [0] :>> hasComposition : 'Device Information Model'::Compositions::Composition;
                part hasComponent [0] :>> hasComponent : Component;
            }
            part def Switch :> Component {
                doc /* leaf {{block(Component)}} that turns on or off an electric current or makes or breaks a circuit.*/
                part hasComposition [0] :>> hasComposition : 'Device Information Model'::Compositions::Composition;
                part hasComponent [0] :>> hasComponent : Component;
            }
            part def Tensioner :> Component {
                doc /* leaf {{block(Component)}} that provides or applies a stretch or strain to another mechanism.*/
                part hasComposition [0] :>> hasComposition : 'Device Information Model'::Compositions::Composition;
                part hasComponent [0] :>> hasComponent : Component;
            }
            part def Water :> Component {
                doc /* leaf {{block(Component)}} composed of $$H_2 O$$.*/
                part hasComposition [0] :>> hasComposition : 'Device Information Model'::Compositions::Composition;
                part hasComponent [0] :>> hasComponent : Component;
            }
            part def Wire :> Component {
                doc /* leaf {{block(Component)}} composed of a string like piece or filament of relatively rigid or flexible material provided in a variety of diameters.*/
                part hasComposition [0] :>> hasComposition : 'Device Information Model'::Compositions::Composition;
                part hasComponent [0] :>> hasComponent : Component;
            }
            part def SensingElement :> Component {
                doc /* leaf {{block(Component)}} that provides a signal or measured value.*/
                part hasComposition [0] :>> hasComposition : 'Device Information Model'::Compositions::Composition;
                part hasComponent [0] :>> hasComponent : Component;
            }
            part def CoolingTower :> Component {
                doc /* leaf {{block(Component)}} composed of a heat exchange system that uses a fluid to transfer heat to the atmosphere.*/
                part hasComposition [0] :>> hasComposition : 'Device Information Model'::Compositions::Composition;
                part hasComponent [0] :>> hasComponent : Component;
            }
            part def RemovalPot :> Component {
                doc /* leaf {{block(Component)}} that is a {{block(Pot)}} for a tool that has to be removed from a {{block(ToolMagazine)}} or {{block(Turret)}} to a location outside of the piece of equipment.*/
                part hasComposition [0] :>> hasComposition : 'Device Information Model'::Compositions::Composition;
                part hasComponent [0] :>> hasComponent : Component;
            }
            part def Gripper :> Component {
                doc /* leaf {{block(Component)}} that holds a part, stock material, or any other item in place.*/
                part hasComposition [0] :>> hasComposition : 'Device Information Model'::Compositions::Composition;
                part hasComponent [0] :>> hasComponent : Component;
            }
            part def StagingPot :> Component {
                doc /* leaf {{block(Component)}} that is a {{block(Pot)}} for a tool that is awaiting transfer to a {{block(ToolMagazine)}} or {{block(Turret)}} from outside of the piece of equipment.*/
                part hasComposition [0] :>> hasComposition : 'Device Information Model'::Compositions::Composition;
                part hasComponent [0] :>> hasComponent : Component;
            }
            part def Brake :> Component {
                doc /* leaf {{block(Component)}} that slows or stops a moving object by the absorption or transfer of the energy of momentum, usually by means of friction, electrical force, or magnetic force.*/
                part hasComposition [0] :>> hasComposition : 'Device Information Model'::Compositions::Composition;
                part hasComponent [0] :>> hasComponent : Component;
            }
            part def Station :> Component {
                doc /* leaf {{block(Component)}} composed of a storage or mounting location for a tool associated with a {{block(Turret)}}, {{block(GangToolBar)}}, or {{block(ToolRack)}}.*/
                part hasComposition [0] :>> hasComposition : 'Device Information Model'::Compositions::Composition;
                part hasComponent [0] :>> hasComponent : Component;
            }
            part def Hopper :> Component {
                doc /* leaf {{block(Component)}} composed of a chamber or bin in which materials are stored temporarily, typically being filled through the top and dispensed through the bottom.*/
                part hasComposition [0] :>> hasComposition : 'Device Information Model'::Compositions::Composition;
                part hasComponent [0] :>> hasComponent : Component;
            }
            part def Belt :> Component {
                doc /* leaf {{block(Component)}} composed of an endless flexible band that transmits motion for a piece of equipment or conveys materials and objects.*/
                part hasComposition [0] :>> hasComposition : 'Device Information Model'::Compositions::Composition;
                part hasComponent [0] :>> hasComponent : Component;
            }
            part def TransferArm :> Component {
                doc /* leaf {{block(Component)}} that physically moves a tool from one location to another.*/
                part hasComposition [0] :>> hasComposition : 'Device Information Model'::Compositions::Composition;
                part hasComponent [0] :>> hasComponent : Component;
            }
            part def Reel :> Component {
                doc /* leaf {{block(Component)}} composed of a rotary storage unit for material.*/
                part hasComposition [0] :>> hasComposition : 'Device Information Model'::Compositions::Composition;
                part hasComponent [0] :>> hasComponent : Component;
            }
            part def Filter :> Component {
                doc /* leaf {{block(Component)}} through which liquids or gases are passed to remove suspended impurities or to recover solids.*/
                part hasComposition [0] :>> hasComposition : 'Device Information Model'::Compositions::Composition;
                part hasComponent [0] :>> hasComponent : Component;
            }
            part def ReturnPot :> Component {
                doc /* leaf {{block(Component)}} that is a {{block(Pot)}} for a tool that has been removed from {{term(spindle)}} or {{block(Turret)}} and awaiting for return to a {{block(ToolMagazine)}}.*/
                part hasComposition [0] :>> hasComposition : 'Device Information Model'::Compositions::Composition;
                part hasComponent [0] :>> hasComponent : Component;
            }
            part def Chain :> Component {
                doc /* leaf {{block(Component)}} composed of interconnected series of objects that band together and are used to transmit motion for a piece of equipment or to convey materials and objects.*/
                part hasComposition [0] :>> hasComposition : 'Device Information Model'::Compositions::Composition;
                part hasComponent [0] :>> hasComponent : Component;
            }
            part def Amplifier :> Component {
                doc /* leaf {{block(Component)}} composed of an electronic component or circuit that amplifies power, electric current, or voltage.*/
                part hasComposition [0] :>> hasComposition : 'Device Information Model'::Compositions::Composition;
                part hasComponent [0] :>> hasComponent : Component;
            }
            part def Vat :> Component {
                doc /* leaf {{block(Component)}} generally composed of an open container.*/
                part hasComposition [0] :>> hasComposition : 'Device Information Model'::Compositions::Composition;
                part hasComponent [0] :>> hasComponent : Component;
            }
            part def ExpiredPot :> Component {
                doc /* leaf {{block(Component)}} that is a {{block(Pot)}} for a tool that is no longer usable for removal from a {{block(ToolMagazine)}} or {{block(Turret)}}.*/
                part hasComposition [0] :>> hasComposition : 'Device Information Model'::Compositions::Composition;
                part hasComponent [0] :>> hasComponent : Component;
            }
            part def Oil :> Component {
                doc /* leaf {{block(Component)}} composed of a viscous liquid.*/
                part hasComposition [0] :>> hasComposition : 'Device Information Model'::Compositions::Composition;
                part hasComponent [0] :>> hasComponent : Component;
            }
            part def Table :> Component {
                doc /* leaf {{block(Component)}} composed of a surface for holding an object or material.*/
                part hasComposition [0] :>> hasComposition : 'Device Information Model'::Compositions::Composition;
                part hasComponent [0] :>> hasComponent : Component;
            }
            part def Chopper :> Component {
                doc /* leaf {{block(Component)}} that breaks material into smaller pieces.*/
                part hasComposition [0] :>> hasComposition : 'Device Information Model'::Compositions::Composition;
                part hasComponent [0] :>> hasComponent : Component;
            }
            part def Valve :> Component {
                doc /* leaf {{block(Component)}} that halts or controls the flow of a liquid, gas, or other material through a passage, pipe, inlet, or outlet.*/
                part hasComposition [0] :>> hasComposition : 'Device Information Model'::Compositions::Composition;
                part hasComponent [0] :>> hasComponent : Component;
            }
            part def Pot :> Component {
                doc /* leaf {{block(Component)}} composed of a tool storage location associated with a {{block(ToolMagazine)}} or {{block(AutomaticToolChanger)}}.*/
                part hasComposition [0] :>> hasComposition : 'Device Information Model'::Compositions::Composition;
                part hasComponent [0] :>> hasComponent : Component;
            }
            part def Transformer :> Component {
                doc /* leaf {{block(Component)}} that transforms electric energy from a source to a secondary circuit.*/
                part hasComposition [0] :>> hasComposition : 'Device Information Model'::Compositions::Composition;
                part hasComponent [0] :>> hasComponent : Component;
            }
            part def ExposureUnit :> Component {
                doc /* leaf {{block(Component)}} that emits a type of radiation.*/
                part hasComposition [0] :>> hasComposition : 'Device Information Model'::Compositions::Composition;
                part hasComponent [0] :>> hasComponent : Component;
            }
            part def Tank :> Component {
                doc /* leaf {{block(Component)}} generally composed of an enclosed container.*/
                part hasComposition [0] :>> hasComposition : 'Device Information Model'::Compositions::Composition;
                part hasComponent [0] :>> hasComponent : Component;
            }
            part def Encoder :> Component {
                doc /* leaf {{block(Component)}} that measures position.*/
                part hasComposition [0] :>> hasComposition : 'Device Information Model'::Compositions::Composition;
                part hasComponent [0] :>> hasComponent : Component;
            }
            part def StorageBattery :> Component {
                doc /* leaf {{block(Component)}} composed of one or more cells in which chemical energy is converted into electricity and used as a source of power. */
                part hasComposition [0] :>> hasComposition : 'Device Information Model'::Compositions::Composition;
                part hasComponent [0] :>> hasComponent : Component;
            }
            part def CircuitBreaker :> Component {
                doc /* leaf {{block(Component)}} that interrupts an electric circuit.*/
                part hasComposition [0] :>> hasComposition : 'Device Information Model'::Compositions::Composition;
                part hasComponent [0] :>> hasComponent : Component;
            }
            part def Motor :> Component {
                doc /* leaf {{block(Component)}} that converts electrical, pneumatic, or hydraulic energy into mechanical energy.*/
                part hasComposition [0] :>> hasComposition : 'Device Information Model'::Compositions::Composition;
                part hasComponent [0] :>> hasComponent : Component;
            }
            part def ExtrusionUnit :> Component {
                doc /* leaf {{block(Component)}} that dispenses liquid or powered materials.*/
                part hasComposition [0] :>> hasComposition : 'Device Information Model'::Compositions::Composition;
                part hasComponent [0] :>> hasComponent : Component;
            }
            part def Galvanomotor :> Component {
                doc /* leaf {{block(Component)}} composed of an electromechanical actuator that produces deflection of a beam of light or energy in response to electric current through its coil in a magnetic field.*/
                part hasComposition [0] :>> hasComposition : 'Device Information Model'::Compositions::Composition;
                part hasComponent [0] :>> hasComponent : Component;
            }
            part def Pump :> Component {
                doc /* leaf {{block(Component)}} that raises, drives, exhausts, or compresses fluids or gases by means of a piston, plunger, or set of rotating vanes.*/
                part hasComposition [0] :>> hasComposition : 'Device Information Model'::Compositions::Composition;
                part hasComponent [0] :>> hasComponent : Component;
            }
            part def Clamp :> Component {
                doc /* leaf {{block(Component)}} that strengthens, support, or fastens objects in place.*/
                part hasComposition [0] :>> hasComposition : 'Device Information Model'::Compositions::Composition;
                part hasComponent [0] :>> hasComponent : Component;
            }
            part def LinearPositionFeedback :> Component {
                doc 
                /* leaf {{block(Component)}} that measures linear motion or position.
                 *
                 * **DEPRECATION WARNING** : May be deprecated in the future. Recommend using {{block(Encoder)}}.*/
                part hasComposition [0] :>> hasComposition : 'Device Information Model'::Compositions::Composition;
                part hasComponent [0] :>> hasComponent : Component;
            }
            part def Workpiece :> Component {
                doc /* leaf {{block(Component)}} composed of an object or material on which a form of work is performed.*/
                part hasComposition [0] :>> hasComposition : 'Device Information Model'::Compositions::Composition;
                part hasComponent [0] :>> hasComponent : Component;
            }
            part def WorkEnvelope :> System {
                doc /* {{block(System)}} composed of the physical process execution space within a piece of equipment.*/
                comment /* Description*/
                doc /* {{block(WorkEnvelope)}} **MAY** provide information regarding the physical workspace and the conditions within that workspace.*/
            }
            part def FeatureOccurrence :> PartOccurrence {
                doc /* {{block(Component)}} that provides information related to an individual {{term(feature)}}.*/
                part observesFeaturePersisitentId [0..1] : 'Observation Information Model'::'Observation Types'::'Event Types'::FeaturePersisitentId;
                part observesFeatureMeasurement [0..1] : 'Observation Information Model'::'Observation Types'::'Event Types'::FeatureMeasurement;
                part observesMeasurementType [0..1] : 'Observation Information Model'::'Observation Types'::'Event Types'::MeasurementType;
                part observesCharacteristicPersistentId [0..1] : 'Observation Information Model'::'Observation Types'::'Event Types'::CharacteristicPersistentId;
                part observesCharacteristicStatus [0..1] : 'Observation Information Model'::'Observation Types'::'Event Types'::CharacteristicStatus;
                part observesUncertainty [0..1] : 'Observation Information Model'::'Observation Types'::'Event Types'::Uncertainty;
                part observesUncertaintyType [0..1] : 'Observation Information Model'::'Observation Types'::'Event Types'::UncertaintyType;
                part observesMeasurementUnits [0..1] : 'Observation Information Model'::'Observation Types'::'Event Types'::MeasurementUnits;
                part observesMeasurementValue [0..1] : 'Observation Information Model'::'Observation Types'::'Event Types'::MeasurementValue;
            }
            connection def {
                end observesFeaturePersisitentId : 'Observation Information Model'::'Observation Types'::'Event Types'::FeaturePersisitentId => target.observesFeaturePersisitentId;
                private end : FeatureOccurrence;
            }
            connection def {
                end observesFeatureMeasurement : 'Observation Information Model'::'Observation Types'::'Event Types'::FeatureMeasurement => target.observesFeatureMeasurement;
                private end : FeatureOccurrence;
            }
            connection def {
                end observesMeasurementType : 'Observation Information Model'::'Observation Types'::'Event Types'::MeasurementType => target.observesMeasurementType;
                private end : FeatureOccurrence;
            }
            connection def {
                end observesCharacteristicPersistentId : 'Observation Information Model'::'Observation Types'::'Event Types'::CharacteristicPersistentId => target.observesCharacteristicPersistentId;
                private end : FeatureOccurrence;
            }
            connection def {
                end observesCharacteristicStatus : 'Observation Information Model'::'Observation Types'::'Event Types'::CharacteristicStatus => target.observesCharacteristicStatus;
                private end : FeatureOccurrence;
            }
            connection def {
                end observesUncertainty : 'Observation Information Model'::'Observation Types'::'Event Types'::Uncertainty => target.observesUncertainty;
                private end : FeatureOccurrence;
            }
            connection def {
                end observesUncertaintyType : 'Observation Information Model'::'Observation Types'::'Event Types'::UncertaintyType => target.observesUncertaintyType;
                private end : FeatureOccurrence;
            }
            connection def {
                end observesMeasurementUnits : 'Observation Information Model'::'Observation Types'::'Event Types'::MeasurementUnits => target.observesMeasurementUnits;
                private end : FeatureOccurrence;
            }
            connection def {
                end observesMeasurementValue : 'Observation Information Model'::'Observation Types'::'Event Types'::MeasurementValue => target.observesMeasurementValue;
                private end : FeatureOccurrence;
            }
            connection def {
                end observesEmergencyStop : 'Observation Information Model'::'Observation Types'::'Event Types'::EmergencyStop => target.observesEmergencyStop;
                private end : Controller;
            }
            connection def {
                end observesSystemCondition : 'Observation Information Model'::'Observation Types'::'Condition Types'::System => target.observesSystemCondition;
                private end : Controller;
            }
            connection def {
                end observesControllerMode : 'Observation Information Model'::'Observation Types'::'Event Types'::ControllerMode => target.observesControllerMode;
                private end : Controller;
            }
            part def AirHandler :> System {
                doc /* system that circulates air or regulates airflow without altering temperature or humidity.*/
            }
            part def Electrode :> Auxiliary {
                doc /* {{block(Auxiliary)}} that is used for many electrical discharge manufacturing processes like welding.*/
            }
            part def CuttingTorch :> Auxiliary {
                doc /* {{block(Auxiliary)}} that employs a concentrated flame to both sever materials through cutting and fuse them together in joining processes.*/
            }
            part def ToolHolder :> System {
                doc /* {{block(System)}} that securely interfaces a {{block(Component)}} with a {{block(Device)}}*/
                comment /* Description*/
                doc /* It is the part of a piece of equipment that interacts with the manufacturing process.*/
            }
            part def PinTool :> System {
                doc /* {{block(System)}} composed of a tool that performs the work for a Friction Stir Welding process*/
                comment /* Description*/
                doc /* It is the part of a piece of equipment that interacts with the manufacturing process.*/
            }
            doc 
            /* This section provides semantic information for the types of {{block(Component)}}. 
             *
             * > Note: In the {{term(XML)}} representation, {{block(Component)}} entities are defined into two major categories:
             *
             * > * {{term(top level)}} {{block(Component)}} entities that {{termplural(organize)}} the most significant physical or logical functions of a piece of equipment (see {{sect(Part Properties of Device)}}).  They **MAY** also be used as {{term(lower level)}} {{block(Component)}} entities; as required. See {{package(Component Organizer Types)}}.
             *
             * > * {{term(lower level)}} {{block(Component)}} entities composed of the sub-parts of the parent {{block(Component)}} to provide more clarity and granularity to the physical or logical structure of the {{term(top level)}} {{block(Component)}} entities.
             *
             * This section provides guidance for the most common relationships between {{block(Component)}} types.  However, all {{block(Component)}} types **MAY** be used in any configuration, as required, to fully describe a piece of equipment.
             *
             * As described in {{package(Components)}}, {{block(Component)}} is an abstract entity and will be always realized by a specific {{block(Component)}} type.*/
        }
        connection def Description {
            end hasDescription : Description => target.hasDescription;
            doc /* See {{sect(Description)}}.*/
            private end : Component;
        }
        connection def Compositions {
            end isCompositionOf : Component => hasComposition.'Device Information Model'::Compositions::Composition::isCompositionOf;
            end hasComposition : 'Device Information Model'::Compositions::Composition => isCompositionOf.hasComposition;
            doc /* {{block(Compositions)}} groups one or more {{block(Composition)}} entities. See {{package(Compositions)}}.*/
        }
        connection def Components {
            end hasComponent : Component => isComponentOf.hasComponent;
            end isComponentOf : Component => hasComponent.'Device Information Model'::Components::Component::isComponentOf;
            doc /* {{block(Components)}} groups one or more {{block(Component)}} entities.*/
        }
        connection def Configuration {
            end isConfigurationFor : Component => hasConfiguration.'Device Information Model'::Configurations::Configuration::isConfigurationFor;
            end hasConfiguration : Configurations::Configuration => isConfigurationFor.hasConfiguration;
            doc /* See {{package(Configurations)}}.*/
        }
        connection def DataItems {
            end isObservedBy : Component => observes.'Device Information Model'::DataItems::DataItem::isObservedBy;
            end observes : 'Device Information Model'::DataItems::DataItem => isObservedBy.observes;
            doc /* {{block(DataItems)}} groups one or more {{block(DataItem)}} entities. See {{package(DataItems)}}.*/
        }
        connection def References {
            end hasReference : 'Device Information Model'::References::Reference => target.hasReference;
            doc /* {{block(References)}} groups one or more {{block(Reference)}} entities associated with the {{block(Component)}}. See {{package(References)}}.*/
            private end : Component;
        }
        package Devices {
            part def Agent :> Device {
                doc /* {{block(Device)}} composed of an {{term(MTConnect Agent)}} and all its connected data sources.*/
                comment /* Description*/
                doc 
                /* An {{block(Agent)}} **MUST** be provided by all {{term(MTConnect Agent)}} implementations.
                 *
                 * An {{block(Agent)}} **MUST** provide notifications when devices are added or changed.
                 *
                 * An {{block(Agent)}} **MUST** provide connection information for each data source currently supplying data to the {{term(MTConnect Agent)}}.
                 *
                 * An {{block(Agent)}} **MAY** provide information about telemetry relating to data sources.
                 *
                 * An {{block(Agent)}} **MAY** provide information about the {{term(MTConnect Agent)}} resource utilization.
                 */
            }
            doc /* This section provides semantic information for the {{block(Device)}} types.*/
        }
        connection def ComponentStream {
            end isOrganizerFor : Component => hasComponentStream.'Observation Information Model'::ComponentStream::isOrganizerFor;
            end hasComponentStream : 'Observation Information Model'::ComponentStream => isOrganizerFor.hasComponentStream;
            doc 
            /* {{block(ComponentStream)}} {{termplural(organize)}} the {{block(Observation)}} entities associated with the {{block(Component)}}.
             *
             * See {{package(Observation Information Model)}} for the {{block(ComponentStream)}} model.
             *
             * > Note 1 to entry: In the {{term(XML)}} representation, {{block(ComponentStream)}} entities **MUST NOT** appear in the {{term(MTConnectDevices Response Document)}}.
             *
             * > Note 2 to entry: In the {{term(XML)}} representation, {{block(ComponentStream)}} entities **MUST** appear only in the {{term(MTConnectStreams Response Document)}}.*/
        }
        doc 
        /* This section provides semantic information for the {{block(Component)}} entity. {{figure(Components)}} shows the {{block(Component)}} model. 
         *
         * ![Components](figures/Components.png "Components"){: width="0.8"}
         *
         * > Note: See {{sect(Components Schema Diagrams)}} for XML schema.
         */
        comment /* Components Model*/
        doc 
        /* {{block(MTConnectDevices)}} provides the physical and logical architecture of a piece of equipment. {{figure(Device Entity Hierarchy Example)}} provides an overview of the entities used in an example of an {{block(MTConnectDevices)}} entity.
         *
         * ![Device Entity Hierarchy Example](figures/Device%20Entity%20Hierarchy%20Example.png "Device Entity Hierarchy Example"){: width="0.8"}
         *
         * > Note 1 to entry: See {{lst(device-entity-hierarchy-example)}} for the {{term(XML)}} representation of the same example.
         *
         * > Note 2 to entry: Example above only shows the {{block(Component)}} and {{block(Composition)}} level hierarchy. For a complete semantics on each kind see {{package(Components)}} and {{package(Compositions)}}.
         *
         * A variety of entities are defined to describe a piece of equipment.  Some of these entities **MUST** always be defined for an {{block(MTConnectDevices)}} entity, while others are optional and **MAY** be used, as required, to provide additional structure.
         *
         * The first, or highest level, entity defined for an {{block(MTConnectDevices)}} entity is {{block(Devices)}}. {{block(Devices)}} is used to group one or more pieces of equipment into a single document.  {{block(Devices)}} **MUST** always be defined for an {{block(MTConnectDevices)}} entity.
         *
         * {{block(Device)}} is the next entity defined for the {{block(MTConnectDevices)}} entity. A separate {{block(Device)}} entity is used to identify each piece of equipment for an {{block(MTConnectDevices)}} entity. Each {{block(Device)}} provides information on the physical and logical structure of the piece of equipment and the data associated with that equipment. {{block(Device)}} can also represent any logical grouping of pieces of equipment that function as a unit or any other data source that provides data through an {{term(agent)}}.
         *
         * One or more {{block(Device)}} entities **MUST** always be defined for an {{block(MTConnectDevices)}} entity.
         *
         * {{block(Components)}} is the next entity defined for the {{block(MTConnectDevices)}} entity. {{block(Components)}} is used to group information describing lower level physical parts or logical functions of a piece of equipment.
         *
         * {{block(Component)}} is the next level of entity defined for the {{block(MTConnectDevices)}} entity. {{block(Component)}} is both an abstract type entity and an {{term(organizer)}} type entity. 
         *
         * As an abstract entity, {{block(Component)}} will always be realized by a specific {{block(Component)}} type defined in {{package(Component Types)}}. Each {{block(Component)}} can also be used to organize information describing {{term(lower level)}} entities or {{termplural(DataItem)}} associated with the {{block(Component)}}.
         *
         * If {{term(lower level)}} entities are described, these entities are by definition child {{block(Component)}} entities of a parent {{block(Component)}}. At this next level, the {{term(lower level)}} child {{block(Component)}} entities are grouped by {{block(Components)}}.
         *
         * A {{block(Component)}} **MAY** be further decomposed into {{block(Composition)}} entities that are grouped by {{block(Compositions)}}. These describe the lowest level basic structural or functional building blocks contained within a {{block(Component)}}. Data provided for a {{block(Component)}} provides more specific meaning when it is associated with one of the {{block(Composition)}} entities of the {{block(Component)}}. The different {{block(Composition)}} types that **MAY** be defined for the {{block(MTConnectDevices)}} entity are defined in {{package(Compositions)}}.
         *
         * This parent-child relationship can continue to any depth required to fully define a piece of equipment.
         *
         * > Note: See {{figure(Device Entity Hierarchy Example)}} for an example.
         */
    }
    package Compositions {
        connection def Description {
            end hasDescription : Components::Description => target.hasDescription;
            doc /* See {{sect(Description)}}.*/
            private end : Composition;
        }
        connection def Configuration {
            end hasConfiguration : Configurations::Configuration => isConfigurationFor.hasConfiguration;
            end isConfigurationFor : Composition => hasConfiguration.'Device Information Model'::Configurations::Configuration::isConfigurationFor;
            doc /* See {{sect(Configurations Model)}}.*/
        }
        abstract part def Composition {
            doc /* functional part of a piece of equipment contained within a {{block(Component)}}.*/
            comment /* Description*/
            private ref part isCompositionOf : Components::Component;
            part hasDescription [0..1] : Components::Description;
            part hasConfiguration [0..1] : Configurations::Configuration;
            attribute id [1] : Profile::DataTypes::ID {
                doc /* unique identifier for the {{block(Composition)}} element.*/
            }
            attribute type [1] : Profile::DataTypes::CompositionTypeEnum {
                doc /* type of {{block(Composition)}}.*/
            }
            attribute name [0..1] : Profile::DataTypes::string {
                doc /* name of the {{block(Composition)}} element.*/
            }
            attribute uuid [0..1] : Profile::DataTypes::UUID {
                doc /* universally unique identifier for the {{block(Composition)}}.*/
            }
            doc /* {{block(Composition)}} **MUST NOT** have child {{block(Component)}}, {{block(Composition)}}, or {{block(DataItems)}} elements.*/
        }
        doc 
        /* This section provides semantic information for the {{block(Composition)}} entity.
         *
         * See {{figure(Components)}} for the {{block(Composition)}} model diagram.
         *
         * ![Component with Compositions Example](figures/Component%20with%20Compositions%20Example.png "Component with Compositions Example"){: width="0.8"}
         *
         * > Note: See {{lst(component-with-compositions-example)}} for the {{term(XML)}} representation of the same example.*/
        comment /* Compositions Model*/
        doc 
        /* {{block(Composition)}} entities are used to describe the lowest level physical building blocks of a piece of equipment contained within a {{block(Component)}}. By referencing a specific {{block(Composition)}} entity, further clarification and meaning to data associated with a specific {{block(Component)}} can be achieved.
         *
         * Both {{block(Component)}} and {{block(Composition)}} entities are {{term(lower level)}} entities representing the sub-parts of the parent {{block(Component)}}.  However, there are distinct differences between {{block(Component)}} and {{block(Composition)}} type entities.
         *
         * {{block(Component)}} entities may be further defined with {{term(lower level)}} {{block(Component)}} entities and may have associated {{termplural(DataItem)}}.
         *
         * {{block(Composition)}} entities represent the lowest level physical part of a piece of equipment.  They **MUST NOT** be further defined with {{term(lower level)}} {{block(Component)}} entities and they **MUST NOT** have {{termplural(DataItem)}} directly associated with them.   They do provide additional information that can be used to enhance the specificity of {{termplural(DataItem)}} associated with the parent {{block(Component)}}.*/
    }
    package DataItems {
        package 'DataItem Types' {
            abstract part def Event :> DataItem {
                doc /* abstract {{block(DataItem)}} that is a discrete piece of information from a piece of equipment. It does not have intermediate values that vary over time.
                 */
                comment /* Description*/
                attribute category [1] :>> category : Profile::DataTypes::CategoryEnum default "EVENT";
                attribute type [1] :>> type : Profile::DataTypes::EventEnum;
                doc /* An {{block(Event)}} is information that, when provided at any specific point in time, represents the current state of the piece of equipment.*/
            }
            abstract part def Sample :> DataItem {
                doc /* abstract {{block(DataItem)}} that is continuously changing or analog data value.
                 */
                comment /* Description*/
                attribute category [1] :>> category : Profile::DataTypes::CategoryEnum default "SAMPLE";
                attribute type [1] :>> type : Profile::DataTypes::SampleEnum;
                attribute units [1] :>> units : Profile::DataTypes::UnitEnum;
                doc /* This data can be measured at any point-in-time and will always produce a result.*/
            }
            abstract part def Condition :> DataItem {
                doc /* abstract {{block(DataItem)}} that is about an entity's status regarding its ability to operate or it provides an indication whether the data reported for the entity is within an expected range.*/
                comment /* Description*/
                attribute category [1] :>> category : Profile::DataTypes::CategoryEnum default "CONDITION";
                attribute type [1] :>> type : Profile::DataTypes::ConditionEnum;
                doc 
                /* {{block(Condition)}} is reported differently than {{block(Sample)}} or {{block(Event)}}.  {{block(Condition)}} **MUST** be reported as {{block(Normal)}}, {{block(Warning)}}, or {{block(Fault)}}.
                 *
                 * All {{block(Sample)}}s **MAY** have associated {{block(Condition)}} states.  {{block(Condition)}} states indicate whether the value for the data is within an expected range and **MUST** be reported as {{block(Normal)}}, or the value is unexpected or out of tolerance for the data and a {{block(Warning)}} or {{block(Fault)}} **MUST** be provided.*/
            }
            doc 
            /* This section provides semantic information for the types of a {{block(DataItem)}}.
             *
             * In the MTConnect Standard, {{block(DataItem)}} are defined and organized based upon the {{property(DataItem::category)}} and {{property(DataItem::type)}}.  The {{property(DataItem::category)}} provides a high level grouping for {{block(DataItem)}}s based on the kind of information that is reported by the data item.
             *
             * These categories are:
             *
             * * `SAMPLE`: A `SAMPLE` reports a continuously variable or analog data value. 
             *
             * * `EVENT`: An `EVENT` reports information representing a functional state, with two or more discrete values, associated with a component or it contains a message.  The data provided may be a numeric value or text.
             *
             * * `CONDITION`: A `CONDITION` reports information about the health of a piece of equipment and its ability to function.
             *
             * The {{property(DataItem::type)}} specifies the specific kind of data that is reported.   For some types of data items, a {{property(DataItem::subType)}} may also be used to differentiate between multiple data items of the same {{property(DataItem::type)}} where the information reported by the data item has a different, but related, meaning.
             *
             * Many types of data items provide two forms of data: a value (reported as either a `SAMPLE` or `EVENT`) and a health status (reported as a `CONDITION`).  These {{block(DataItem)}} types **MAY** be defined in more than one {{property(DataItem::category)}} based on the data that they report.
             */
        }
        part def DataItem {
            doc /* information reported about a piece of equipment.*/
            attribute category [1] : Profile::DataTypes::CategoryEnum {
                doc /* specifies the kind of information provided by a data item.*/
            }
            attribute compositionId [0..1] : Profile::DataTypes::ID {
                doc /* identifier attribute of the {{block(Composition)}} that the reported data is most closely associated.*/
            }
            attribute coordinateSystem [0..1] : Profile::DataTypes::CoordinateSystemEnum {
                doc 
                /* for measured values relative to a coordinate system like {{block(Position)}}, the coordinate system used may be reported.
                 *
                 * **DEPRECATED** in *Version 2.0*. Replaced by {{property(Component::coordinateSystemIdRef)}}. */
            }
            attribute discrete [1] : Profile::DataTypes::boolean default false {
                doc 
                /* indication signifying whether each value reported for the {{term(Observation)}} is significant and whether duplicate values are to be suppressed.
                 *
                 * If a value is not defined for {{property(DataItem::discrete)}}, the default value **MUST** be `false`.*/
            }
            attribute id [1] : Profile::DataTypes::ID {
                doc /* unique identifier for this data item.*/
            }
            attribute name [0..1] : Profile::DataTypes::string {
                doc /* name of the data item.*/
            }
            attribute nativeScale [0..1] : Profile::DataTypes::integer {
                doc /* used to convert the reported value to represent the original measured value.*/
            }
            attribute nativeUnits [0..1] : Profile::DataTypes::NativeUnitEnum {
                doc /* native units of measurement for the reported value of the data item.*/
            }
            attribute sampleRate [0..1] : Profile::DataTypes::float {
                doc /* rate at which successive samples of a data item are recorded by a piece of equipment.*/
            }
            attribute significantDigits [0..1] : Profile::DataTypes::integer {
                doc /* number of significant digits in the reported value.*/
            }
            attribute statistic [0..1] : Profile::DataTypes::StatisticEnum {
                doc /* type of statistical calculation performed on a series of data samples to provide the reported data value.*/
            }
            attribute subType [0..1] : Profile::DataTypes::DataItemSubTypeEnum {
                doc /* sub-categorization of the {{property(DataItem::type)}}.*/
            }
            attribute type [1] : Profile::DataTypes::DataItemTypeEnum {
                doc /* type of data being measured. See {{package(DataItem Types)}}.*/
            }
            attribute units [0..1] : Profile::DataTypes::UnitEnum {
                doc /* unit of measurement for the reported value of the data item.*/
            }
            private ref part isObservedBy [1] : Components::Component;
            attribute representation [0..1] : Profile::DataTypes::RepresentationEnum {
                doc 
                /* description of a means to interpret data consisting of multiple data points or samples reported as a single value.  
                 *
                 * If {{property(DataItem::representation)}} is not specified, it **MUST** be determined to be `VALUE`.
                 */
            }
            part hasSource [0..1] : 'Properties of DataItem'::Source;
            part hasConstraint [0..1] : 'Properties of DataItem'::Constraints;
            part hasFilter [0..*] : 'Properties of DataItem'::Filter;
            part hasInitialValue [0..1] : 'Properties of DataItem'::InitialValue;
            part hasResetTrigger [0..1] : 'Properties of DataItem'::ResetTrigger;
            ref part hasObservation [0..*] : 'Observation Information Model'::Observation;
            part hasDefinition [0..1] : 'Properties of DataItem'::Definition;
            attribute coordinateSystemIdRef [0..1] : Profile::DataTypes::ID {
                doc /* associated {{block(CoordinateSystem)}} context for the {{block(DataItem)}}.*/
            }
            part hasRelationship [0..*] : 'Properties of DataItem'::'Relationship Types for DataItem'::AbstractDataItemRelationship;
        }
        connection def Filters {
            end hasFilter : 'Properties of DataItem'::Filter => target.hasFilter;
            doc /* {{block(Filters)}} groups one or more {{block(Filter)}} entities associated with the {{block(DataItem)}}. */
            private end : DataItem;
        }
        connection def Constraints {
            end hasConstraint : 'Properties of DataItem'::Constraints => target.hasConstraint;
            doc /* {{block(Constraints)}} organizes a set of expected values that can be reported for the {{block(DataItem)}}. See {{sect(Constraints)}}.*/
            private end : DataItem;
        }
        connection def ResetTrigger {
            end hasResetTrigger : 'Properties of DataItem'::ResetTrigger => target.hasResetTrigger;
            private end : DataItem;
        }
        connection def InitialValue {
            end hasInitialValue : 'Properties of DataItem'::InitialValue => target.hasInitialValue;
            private end : DataItem;
        }
        connection def Source {
            end hasSource : 'Properties of DataItem'::Source => target.hasSource;
            doc /* See {{sect(Source)}}.*/
            private end : DataItem;
        }
        connection def Observations {
            end madeForDataItem : DataItem => hasObservation.'Observation Information Model'::Observation::madeForDataItem;
            end hasObservation : 'Observation Information Model'::Observation => madeForDataItem.hasObservation;
            doc 
            /* {{block(Observations)}} groups one or more {{block(Observation)}} entities made for the {{block(DataItem)}} entity. 
             *
             * {{block(Component)}} {{termplural(observe)}} {{block(DataItem)}} entities to create {{block(Observation)}} entities for the {{block(DataItem)}} entities.
             *
             * See {{package(Observation Information Model)}} for the {{block(Observation)}} model.
             *
             * > Note 1 to entry: In the {{term(XML)}} representation, {{block(Observation)}} entities **MUST NOT** appear in the {{term(MTConnectDevices Response Document)}}.
             *
             * > Note 2 to entry: In the {{term(XML)}} representation, {{block(Observation)}} entities **MUST** appear only in the {{term(MTConnectStreams Response Document)}}.*/
        }
        connection def Definition {
            end hasDefinition : 'Properties of DataItem'::Definition => target.hasDefinition;
            doc /* See {{sect(Definition)}}.*/
            private end : DataItem;
        }
        package 'Properties of DataItem' {
            part def ResetTrigger {
                doc /* type of event that may cause a reset to occur.*/
                attribute value [1] : Profile::DataTypes::ResetTriggerEnum {
                    doc /* type of {{block(ResetTrigger)}}.*/
                }
            }
            part def Source {
                doc /* identifies the {{block(Component)}}, {{block(DataItem)}}, or {{block(Composition)}} from which a measured value originates.*/
                attribute componentId [0..1] : Profile::DataTypes::ID {
                    doc /* identifier of the {{block(Component)}} that represents the physical part of a piece of equipment where the data represented by the {{block(DataItem)}} originated.*/
                }
                attribute compositionId [0..1] : Profile::DataTypes::ID {
                    doc /* identifier of the {{block(Composition)}} that represents the physical part of a piece of equipment where the data represented by the {{block(DataItem)}} originated.*/
                }
                attribute dataItemId [0..1] : Profile::DataTypes::ID {
                    doc /* identifier of the {{block(DataItem)}} that represents the originally measured value of the data referenced by this {{block(DataItem)}}.*/
                }
                attribute value [0..1] : Profile::DataTypes::string {
                    doc /* identifier of the source entity.*/
                }
            }
            part def InitialValue {
                doc /* starting value for a {{block(DataItem)}} as well as the value to be set for the {{block(DataItem)}} after a reset event.*/
                attribute value [1] : Profile::DataTypes::string;
            }
            abstract part def Filter {
                doc /* provides a means to control when an {{term(agent)}} records updated information for a {{block(DataItem)}}. */
                attribute type [1] : Profile::DataTypes::FilterEnum {
                    doc /* type of {{block(Filter)}}.*/
                }
                attribute value [0..1] : Profile::DataTypes::float;
            }
            part def Constraints {
                doc /* {{termplural(organize)}} a set of expected values that can be reported for a {{block(DataItem)}}.*/
                attribute Maximum [0..1] : Profile::DataTypes::float {
                    doc 
                    /* numeric upper constraint.
                     *
                     * If the data reported for a data item is a range of numeric values, the expected value reported **MAY** be described with an upper limit defined by this constraint.*/
                }
                attribute Minimum [0..1] : Profile::DataTypes::float {
                    doc 
                    /* numeric lower constraint.
                     *
                     * If the data reported for a data item is a range of numeric values, the expected value reported **MAY** be described with a lower limit defined by this constraint.*/
                }
                attribute Nominal [0..1] : Profile::DataTypes::float {
                    doc /* numeric target or expected value.*/
                }
                attribute Value [0..*] : Profile::DataTypes::string {
                    doc 
                    /* single data value that is expected to be reported for a {{block(DataItem)}}.
                     *
                     * {{property(Constraints::Value)}} **MUST NOT** be used in conjunction with any other {{block(Constraint)}} elements.*/
                }
                part hasFilter [0..1] : Filter;
            }
            package 'Properties of Definition' {
                part def CellDefinition {
                    doc /* semantic definition of a {{block(Cell)}}.*/
                    attribute units [0..1] : Profile::DataTypes::UnitEnum {
                        doc /* same as {{property(DataItem::units)}}. See {{sect(Value Properties of DataItem)}}.*/
                    }
                    attribute key [0..1] : Profile::DataTypes::string {
                        doc 
                        /* unique identification of the {{block(Cell)}} in the {{block(Definition)}}. 
                         *
                         * The description applies to all {{block(Cell)}} {{termplural(observation)}} having this {{property(CellDefinition::key)}}.*/
                    }
                    attribute type [0..1] : Profile::DataTypes::DataItemTypeEnum {
                        doc /* same as {{property(DataItem::type)}}. See {{package(DataItem Types)}}.*/
                    }
                    attribute subType [0..1] : Profile::DataTypes::DataItemSubTypeEnum {
                        doc /* same as {{property(DataItem::subType)}}. See {{sect(DataItem)}}.*/
                    }
                    attribute keyType [0..1] : Profile::DataTypes::DataItemTypeEnum {
                        doc /* {{property(DataItem::type)}} that defines the meaning of {{property(CellDefinition::key)}}.*/
                    }
                    private attribute Description [0..1] : Profile::DataTypes::string {
                        doc /* textual description for {{block(CellDefinition)}}.*/
                    }
                }
                part def EntryDefinition {
                    doc /* semantic definition of an {{block(Entry)}}.*/
                    attribute key [0..1] : Profile::DataTypes::string {
                        doc 
                        /* unique identification of the {{block(Entry)}} in the {{block(Definition)}}. 
                         *
                         * The description applies to all {{block(Entry)}} {{termplural(observation)}} having this {{property(EntryDefinition::key)}}.*/
                    }
                    attribute units [0..1] : Profile::DataTypes::UnitEnum {
                        doc /* same as {{property(DataItem::units)}}. See {{sect(Value Properties of DataItem)}}.*/
                    }
                    part hasCellDefinition [0..*] : CellDefinition;
                    attribute type [0..1] : Profile::DataTypes::DataItemTypeEnum {
                        doc /* same as {{property(DataItem::type)}}. See {{package(DataItem Types)}}.*/
                    }
                    attribute subType [0..1] : Profile::DataTypes::DataItemSubTypeEnum {
                        doc /* same as {{property(DataItem::subType)}}. See {{sect(DataItem)}}.*/
                    }
                    attribute keyType [0..1] : Profile::DataTypes::DataItemTypeEnum {
                        doc /* {{property(DataItem::type)}} that defines the meaning of {{property(EntryDefinition::key)}}.*/
                    }
                    private attribute Description [0..1] : Profile::DataTypes::string {
                        doc /* textual description for {{block(EntryDefinition)}}.*/
                    }
                }
                connection def CellDefinitions {
                    end hasCellDefinition : CellDefinition => target.hasCellDefinition;
                    doc /* {{block(CellDefinitions)}} groups one or more {{block(CellDefinition)}} entities if {{property(DataItem::representation)}} is `TABLE`. See {{sect(CellDefinition)}}.*/
                    private end : EntryDefinition;
                }
                doc /* This section provides semantic information for the elements of the {{block(Definition)}} for a {{block(DataItem)}}.*/
            }
            part def Definition {
                doc /* defines the meaning of {{block(Entry)}} and {{block(Cell)}} entities when the associated {{property(DataItem::representation)}} is either `DATA_SET` or `TABLE`.*/
                part hasCellDefinition [0..*] : 'Properties of Definition'::CellDefinition;
                part hasEntryDefinition [0..*] : 'Properties of Definition'::EntryDefinition;
                private attribute Description [0..1] : Profile::DataTypes::string {
                    doc /* textual description for {{block(Definition)}}.*/
                }
            }
            connection def CellDefinitions {
                end hasCellDefinition : 'Properties of Definition'::CellDefinition => target.hasCellDefinition;
                doc /* {{block(CellDefinitions)}} groups one or more {{block(CellDefinition)}} entities. See {{sect(CellDefinition)}}.*/
                private end : Definition;
            }
            connection def EntryDefinitions {
                end hasEntryDefinition : 'Properties of Definition'::EntryDefinition => target.hasEntryDefinition;
                doc /* {{block(EntryDefinitions)}} groups one or more {{block(EntryDefinition)}} entities. See {{sect(EntryDefinition)}}.*/
                private end : Definition;
            }
            package 'Relationship Types for DataItem' {
                part def SpecificationRelationship :> AbstractDataItemRelationship {
                    doc /* {{block(AbstractDataItemRelationship)}} that provides a semantic reference to another {{block(Specification)}} described by {{property(SpecificationRelationship::type)}} and {{property(SpecificationRelationship::idRef)}}.*/
                    attribute type [1] : Profile::DataTypes::SpecificationRelationshipTypeEnum {
                        doc /* specifies how the {{block(Specification)}} is related.*/
                    }
                }
                part def DataItemRelationship :> AbstractDataItemRelationship {
                    doc /* {{block(AbstractDataItemRelationship)}} that provides a semantic reference to another {{block(DataItem)}} described by {{property(DataItemRelationship::type)}}.*/
                    attribute type [1] : Profile::DataTypes::DataItemRelationshipTypeEnum {
                        doc /* specifies how the {{block(DataItem)}} is related.*/
                    }
                }
                abstract part def AbstractDataItemRelationship {
                    doc /* association between a {{block(DataItem)}} and another entity.*/
                    comment /* Description*/
                    attribute idRef [1] : Profile::DataTypes::ID {
                        doc /* reference to the related entity's `id`.*/
                    }
                    attribute name [0..1] : Profile::DataTypes::string {
                        doc /* descriptive name associated with this {{block(AbstractDataItemRelationship)}}.*/
                    }
                    doc /* {{block(AbstractDataItemRelationship)}} is an abstract entity and hence will be realized by specific {{block(AbstractDataItemRelationship)}} types in an {{block(MTConnectDevices)}} entity. See {{package(Relationship Types for DataItem)}}.*/
                }
                doc /* This section provides semantic information for the types of {{block(AbstractDataItemRelationship)}} that can be defined for a {{block(DataItem)}}.*/
            }
            connection def Filter {
                end hasFilter : Filter => target.hasFilter;
                doc /* **DEPRECATED** in *MTConnect Version 1.4*. Moved to the {{block(Filters)}}. See {{package(Properties of DataItem)}}.*/
                private end : Constraints;
            }
            part def MinimumDeltaFilter :> Filter {
                doc /* {{def(FilterEnum::MINIMUM_DELTA)}}*/
                attribute type [1] :>> type : Profile::DataTypes::FilterEnum default type::MINIMUM_DELTA;
            }
            part def PeriodFilter :> Filter {
                doc /* {{def(FilterEnum::PERIOD)}}*/
                attribute type [1] :>> type : Profile::DataTypes::FilterEnum :> type default type::PERIOD;
                attribute value :>> value : Profile::DataTypes::SECOND;
            }
            doc 
            /* This section provides additional semantic information for the Part Properties of {{block(DataItem)}}.
             *
             * > Note: See {{sect(DataItems Schema Diagrams)}} for XML schema of the elements for {{block(DataItem)}}.*/
        }
        connection def Relationships {
            end hasRelationship : 'Properties of DataItem'::'Relationship Types for DataItem'::AbstractDataItemRelationship => target.hasRelationship;
            doc /* {{block(Relationships)}} groups one or more {{block(DataItemRelationship)}} and {{block(SpecificationRelationship)}}. See {{package(Relationships)}}.*/
            private end : DataItem;
        }
        doc 
        /* This section provides semantic information for the {{block(DataItem)}} entity. {{figure(DataItems)}} shows the {{block(DataItem)}} model. 
         *
         * ![DataItems](figures/DataItems.png "DataItems"){: width="0.8"}
         *
         * > Note: See {{sect(DataItems Schema Diagrams)}} for XML schema.*/
        comment /* DataItems Model*/
        doc 
        /* For an {{block(MTConnectDevices)}} entity, {{termplural(DataItem)}} describe data that can be reported by a piece of equipment and are associated with {{block(Device)}} and {{block(Component)}} entities. While the {{termplural(DataItem)}} describe the data that can be reported by a piece of equipment as an {{block(MTConnectDevices)}} entity, the actual data values are provided by the {{block(MTConnectStreams)}} entity in the {{term(MTConnectStreams Response Document)}}. See {{package(Observation Information Model)}} for detail on the reported values.
         *
         * Each {{term(DataItem)}} **SHOULD** be modeled for the {{block(MTConnectDevices)}} entity such that it is associated with the entity that the reported data directly applies.
         *
         * {{block(DataItem)}} describes specific types of {{termplural(DataItem)}} that represent a numeric value, a functioning state, or a health status reported by a piece of equipment. {{block(DataItem)}} provides a detailed description for each {{term(DataItem)}} that is reported; it defines the type of data being reported and an array of optional attributes that further describe that data. The different types of {{block(DataItem)}} elements are defined in {{package(DataItem Types)}}.*/
    }
    package References {
        abstract part def Reference {
            doc /* pointer to information that is associated with another entity defined elsewhere in the {{block(MTConnectDevices)}} entity for a piece of equipment.*/
            comment /* Description*/
            attribute idRef [1] : Profile::DataTypes::ID {
                doc /* pointer to the `id` of an entity that contains the information to be associated with this entity.*/
            }
            attribute name [0..1] : Profile::DataTypes::string {
                doc /*  name of an element or a piece of equipment.*/
            }
            private attribute dataItemId [1] : Profile::DataTypes::ID {
                doc /* pointer to the {{property(DataItem::id)}} that contains the information to be associated with this entity.*/
            }
            private attribute refDataItemId [1] : Profile::DataTypes::ID {
                doc /* pointer to the {{property(DataItem::id)}} that contains the information to be associated with this entity.*/
            }
            doc /* {{block(Reference)}} is an abstract entity and will be realized by a specific {{block(Reference)}} type for an {{block(MTConnectDevices)}} entity. See {{sect(ComponentRef)}} and {{sect(DataItemRef)}}.*/
        }
        part def DataItemRef :> Reference {
            doc /* {{block(Reference)}} that is a pointer to a {{block(DataItem)}} associated with another entity defined for a piece of equipment.*/
            comment /* Description*/
            private ref part idRef [1] :>> idRef : DataItems::DataItem {
                doc /* pointer to the {{property(DataItem::id)}} that contains the information to be associated with this entity.*/
            }
            doc /* {{block(DataItemRef)}} allows the data associated with a {{block(DataItem)}} defined in another entity to be directly associated with this entity.*/
        }
        part def ComponentRef :> Reference {
            doc /* {{block(Reference)}} that is a pointer to all of the information associated with another entity defined for a piece of equipment.
             */
            comment /* Description*/
            private ref part idRef [1] :>> idRef : Components::Component {
                doc /* pointer to the {{property(Component::id)}} that contains the information to be associated with this entity.*/
            }
            doc /* {{block(ComponentRef)}} allows all of the information of ({{term(lower level)}} {{block(Component)}} entities that is associated with the other entity to be directly associated with this entity.*/
        }
        private connection def {
            end idRef :>> id::idRef : DataItems::DataItem => id.'Device Information Model'::References::DataItemRef::idRef;
            private end id : DataItemRef;
        }
        private connection def {
            end idRef :>> id::idRef : Components::Component => id.'Device Information Model'::References::ComponentRef::idRef;
            private end id : ComponentRef;
        }
        doc 
        /* This section provides semantic information for the {{block(Reference)}} entity. {{figure(References)}} shows the {{block(Reference)}} model. 
         *
         * {{block(Reference)}} may be modeled as part of a {{block(Device)}}, {{block(Component)}} or {{block(Interface)}} type.
         *
         * ![References](figures/References.png "References"){: width="0.8"}
         *
         * > Note: See {{sect(References Schema Diagrams)}} for XML schema of {{block(Reference)}} and its types.*/
        comment /* References Model*/
        doc /* {{block(References)}} {{termplural(organize)}} pointers to information defined elsewhere within the {{block(MTConnectDevices)}} entity for a piece of equipment. It is an efficient method to associate information with an element without duplicating any of the data or structure.*/
    }
    package Configurations {
        package CoordinateSystems {
            part def CoordinateSystem {
                doc /* reference system that associates a unique set of n parameters with each point in an n-dimensional space. {{cite(ISO 10303-218:2004)}}*/
                comment /* Description*/
                attribute id [1] : Profile::DataTypes::ID {
                    doc /* unique identifier for the coordinate system.*/
                }
                attribute name [0..1] : Profile::DataTypes::string {
                    doc /* name of the coordinate system.*/
                }
                attribute nativeName [0..1] : Profile::DataTypes::string {
                    doc /* manufacturer's name or users name for the coordinate system.*/
                }
                attribute parentIdRef [0..1] : Profile::DataTypes::ID {
                    doc /* pointer to the {{property(CoordinateSystem::id)}}.*/
                }
                part hasOrigin [0..1] : AbstractOrigin;
                part hasTransformation [0..1] : 'Device Information Model'::Configurations::CoordinateSystems::Transformation;
                attribute type [1] : Profile::DataTypes::CoordinateSystemTypeEnum {
                    doc /* type of coordinate system.*/
                }
                attribute uuid [0..1] : Profile::DataTypes::UUID {
                    doc /* {{term(UUID)}} for the coordinate system.*/
                }
                attribute Description [0..1] : Profile::DataTypes::string {
                    doc /* natural language description of the {{block(CoordinateSystem)}}.*/
                }
                doc /* At most only one of {{block(Origin)}} or {{block(Transformation)}} **MUST** be defined for a {{block(CoordinateSystem)}}.*/
            }
            connection def Transformation {
                end hasTransformation : 'Device Information Model'::Configurations::CoordinateSystems::Transformation => target.hasTransformation;
                doc /* See {{sect(Transformation)}}.*/
                private end : CoordinateSystem;
            }
            connection def Origin {
                end hasOrigin : AbstractOrigin => target.hasOrigin;
                doc /* See {{sect(Origin)}}.*/
                private end : CoordinateSystem;
            }
            part def Origin :> AbstractOrigin {
                doc /* coordinates of the origin position of a coordinate system.*/
                private attribute value [0..1] : Profile::DataTypes::float3d;
            }
            part def Transformation {
                doc /* process of transforming to the origin position of the coordinate system from a parent coordinate system using {{block(Translation)}} and {{block(Rotation)}}.*/
                comment /* Description*/
                part hasTranslation [0..1] : AbstractTranslation;
                part hasRotation [0..1] : AbstractRotation;
                doc /* At a minimum, a {{block(Translation)}} or a {{block(Rotation)}} **MUST** be defined for a {{block(Transformation)}}.*/
            }
            connection def Rotation {
                end hasRotation : AbstractRotation => target.hasRotation;
                doc /* See {{sect(Rotation)}}.*/
                private end : 'Device Information Model'::Configurations::CoordinateSystems::Transformation;
            }
            connection def Translation {
                end hasTranslation : AbstractTranslation => target.hasTranslation;
                doc /* See {{sect(Translation)}}.*/
                private end : 'Device Information Model'::Configurations::CoordinateSystems::Transformation;
            }
            abstract part def AbstractRotation {
                doc /* rotations about X, Y, and Z axes are expressed in A, B, and C respectively within a 3-dimensional vector. 
                 */
            }
            abstract part def AbstractTranslation {
                doc /* translations along X, Y, and Z axes are expressed as x,y, and z respectively within a 3-dimensional vector. */
            }
            abstract part def AbstractOrigin {
                doc /* coordinates of the origin position of a coordinate system.*/
            }
            part def OriginDataSet :> 'Observation Information Model'::Representations::DataSet, AbstractOrigin {
                doc /* coordinates of the origin position of a coordinate system represented as a dataset.*/
                attribute X [0..1] : Profile::DataTypes::MILLIMETER {
                    doc /* x-coordinate.*/
                }
                attribute Y [0..1] : Profile::DataTypes::MILLIMETER {
                    doc /* y-coordinate.*/
                }
                attribute Z [0..1] : Profile::DataTypes::MILLIMETER {
                    doc /* x-coordinate.*/
                }
            }
            part def Translation :> AbstractTranslation {
                doc /* translations along X, Y, and Z axes are expressed as x,y, and z respectively within a 3-dimensional vector. */
                private attribute value [0..1] : Profile::DataTypes::float3d;
            }
            part def TranslationDataSet :> 'Observation Information Model'::Representations::DataSet, AbstractTranslation {
                doc /* translations along X, Y, and Z axes are expressed as x,y, and z respectively within a 3-dimensional vector represented as a dataset.*/
                attribute X [0..1] : Profile::DataTypes::MILLIMETER {
                    doc /* translation along X axis.*/
                }
                attribute Y [0..1] : Profile::DataTypes::MILLIMETER {
                    doc /* translation along Y axis.*/
                }
                attribute Z [0..1] : Profile::DataTypes::MILLIMETER {
                    doc /* translation along Z axis.*/
                }
            }
            part def RotationDataSet :> 'Observation Information Model'::Representations::DataSet, AbstractRotation {
                doc /* rotations about X, Y, and Z axes are expressed in A, B, and C respectively within a 3-dimensional vector represented as a dataset.
                 */
                attribute A [0..1] : Profile::DataTypes::DEGREE {
                    doc /* rotation about X axis.*/
                }
                attribute B [0..1] : Profile::DataTypes::DEGREE {
                    doc /* rotation about Y axis.*/
                }
                attribute C [0..1] : Profile::DataTypes::DEGREE {
                    doc /* rotation about Z axis.*/
                }
            }
            part def Rotation :> AbstractRotation {
                doc /* rotations about X, Y, and Z axes are expressed in A, B, and C respectively within a 3-dimensional vector. 
                 */
                private attribute value [0..1] : Profile::DataTypes::float3d;
            }
            doc 
            /* This section provides semantic information for the {{block(CoordinateSystem)}} entity.
             *
             * ![CoordinateSystem](figures/CoordinateSystem.png "CoordinateSystem"){: width="0.8"}
             *
             * > Note: See {{sect(Configuration Schema Diagrams)}} for XML schema.
             *
             * ![CoordinateSystem Example](figures/CoordinateSystem%20Example.png "CoordinateSystem Example"){: width="0.8"}
             *
             * > Note: See {{lst(coordinatesystem-example)}} for the {{term(XML)}} representation of the same example.*/
        }
        package Motion {
            part def Motion {
                doc /* movement of the component relative to a coordinate system. */
                comment /* Description*/
                attribute actuation [1] : Profile::DataTypes::MotionActuationTypeEnum {
                    doc /* describes if this component is actuated directly or indirectly as a result of other motion.*/
                }
                attribute coordinateSystemIdRef [1] : Profile::DataTypes::ID {
                    doc /* coordinate system within which the kinematic motion occurs.*/
                }
                attribute id [1] : Profile::DataTypes::ID {
                    doc /* unique identifier for this element.*/
                }
                attribute parentIdRef [0..1] : Profile::DataTypes::ID {
                    doc 
                    /* pointer to the {{property(Motion::id)}}.
                     *
                     * The kinematic chain connects all components using the parent relations. All motion is connected to the motion of the parent. The first node in the chain will not have a parent.*/
                }
                attribute type [1] : Profile::DataTypes::MotionTypeEnum {
                    doc /* type of motion.*/
                }
                part hasAxis [0..1] : AbstractAxis;
                part hasOrigin [0..1] : CoordinateSystems::AbstractOrigin;
                part hasTransformation [0..1] : CoordinateSystems::Transformation;
                private attribute Description [0..1] : Profile::DataTypes::string {
                    doc /* textual description for {{block(Motion)}}.*/
                }
                doc 
                /* {{block(Motion)}} specifies the kinematic chain of the {{block(component)}} entities.
                 *
                 * At most only one of {{block(Origin)}} or {{block(Transformation)}} **MUST** be defined for a {{block(Motion)}}.*/
            }
            abstract part def AbstractAxis {
                doc /* axis along or around which the {{block(Component)}} moves relative to a coordinate system.*/
            }
            connection def Transformation {
                end hasTransformation : CoordinateSystems::Transformation => target.hasTransformation;
                doc /* See {{sect(Transformation)}}.*/
                private end : Configurations::Motion::Motion;
            }
            connection def Axis {
                end hasAxis : AbstractAxis => target.hasAxis;
                doc /* See {{sect(Axis)}}.*/
                private end : Configurations::Motion::Motion;
            }
            connection def Origin {
                end hasOrigin : CoordinateSystems::AbstractOrigin => target.hasOrigin;
                doc /* See {{sect(Origin)}}.*/
                private end : Configurations::Motion::Motion;
            }
            part def AxisDataSet :> 'Observation Information Model'::Representations::DataSet, AbstractAxis {
                doc /* axis along or around which the {{block(Component)}} moves relative to a coordinate system represented as a dataset.*/
                attribute X [0..1] : Profile::DataTypes::float {
                    doc /* x-component of {{block(Axis)}}.*/
                }
                attribute Y [0..1] : Profile::DataTypes::float {
                    doc /* y-component of {{block(Axis)}}.*/
                }
                attribute Z [0..1] : Profile::DataTypes::float {
                    doc /* z-component of {{block(Axis)}}.*/
                }
            }
            part def Axis :> AbstractAxis {
                doc /* axis along or around which the {{block(Component)}} moves relative to a coordinate system.*/
                private attribute value [0..1] : Profile::DataTypes::float3d;
            }
            doc 
            /* This section provides semantic information for the {{block(Motion)}} entity.
             *
             * ![Motion](figures/Motion.png "Motion"){: width="0.8"}
             *
             * > Note: See {{sect(Configuration Schema Diagrams)}} for XML schema.
             *
             * ![Motion Example](figures/Motion%20Example.png "Motion Example"){: width="0.8"}
             *
             * > Note: See {{lst(motion-example)}} for the {{term(XML)}} representation of the same example.*/
        }
        package Specifications {
            part def Specification {
                doc /* design characteristics for a piece of equipment.*/
                attribute type [1] : Profile::DataTypes::DataItemTypeEnum {
                    doc /* same as {{property(DataItem::type)}}. See {{package(DataItem Types)}}.*/
                }
                attribute subType [0..1] : Profile::DataTypes::DataItemSubTypeEnum {
                    doc /* same as {{property(DataItem::subType)}}. See {{sect(DataItem)}}.*/
                }
                attribute dataItemIdRef [0..1] : Profile::DataTypes::ID {
                    doc /* reference to the {{property(DataItem::id)}} associated with this entity.*/
                }
                attribute units [0..1] : Profile::DataTypes::UnitEnum {
                    doc /* same as {{property(DataItem::units)}}. See {{sect(DataItem)}}.*/
                }
                attribute compositionIdRef [0..1] : Profile::DataTypes::ID {
                    doc /* reference to the {{property(Composition::id)}} associated with this entity.*/
                }
                attribute name [0..1] : Profile::DataTypes::string {
                    doc /* {{property(Specification::name)}} provides additional meaning and differentiates between {{block(Specification)}} entities.*/
                }
                attribute coordinateSystemIdRef [0..1] : Profile::DataTypes::ID {
                    doc /* references the {{block(CoordinateSystem)}} for geometric {{block(Specification)}} elements.*/
                }
                attribute id [0..1] : Profile::DataTypes::ID {
                    doc /* unique identifier for this {{block(Specification)}}.*/
                }
                attribute originator [1] : Profile::DataTypes::OriginatorEnum default originator::MANUFACTURER {
                    doc /* reference to the creator of the {{block(Specification)}}.*/
                }
                part hasMaximum [0..1] : Maximum;
                part hasUpperLimit [0..1] : 'Device Information Model'::Configurations::Specifications::UpperLimit;
                part hasLowerWarning [0..1] : 'Device Information Model'::Configurations::Specifications::LowerWarning;
                part hasLowerLimit [0..1] : 'Device Information Model'::Configurations::Specifications::LowerLimit;
                part hasUpperWarning [0..1] : 'Device Information Model'::Configurations::Specifications::UpperWarning;
                part hasNominal [0..1] : 'Device Information Model'::Configurations::Specifications::Nominal;
                part hasMinimum [0..1] : Minimum;
            }
            part def ProcessSpecification :> Specification {
                doc /* {{block(Specification)}} that provides information used to assess the conformance of a variable to process requirements.*/
                part hasSpecificationLimits [0..1] : SpecificationLimits;
                part hasControlLimits [0..1] : ControlLimits;
                part hasAlarmLimits [0..1] : AlarmLimits;
            }
            part def ControlLimits {
                doc /* set of limits that is used to indicate whether a process variable is stable and in control.*/
                part upperLimit [0..1] : 'Device Information Model'::Configurations::Specifications::UpperLimit;
                part upperWarning [0..1] : 'Device Information Model'::Configurations::Specifications::UpperWarning;
                part lowerWarning [0..1] : 'Device Information Model'::Configurations::Specifications::LowerWarning;
                part nominal [0..1] : 'Device Information Model'::Configurations::Specifications::Nominal;
                part lowerLimit [0..1] : 'Device Information Model'::Configurations::Specifications::LowerLimit;
            }
            part def AlarmLimits {
                doc /* set of limits that is used to trigger warning or alarm indicators.*/
                part upperLimit [0..1] : 'Device Information Model'::Configurations::Specifications::UpperLimit;
                part upperWarning [0..1] : 'Device Information Model'::Configurations::Specifications::UpperWarning;
                part lowerLimit [0..1] : 'Device Information Model'::Configurations::Specifications::LowerLimit;
                part lowerWarning [0..1] : 'Device Information Model'::Configurations::Specifications::LowerWarning;
            }
            part def SpecificationLimits {
                doc /* set of limits that define a range of values designating acceptable performance for a variable.*/
                part upperLimit [0..1] : 'Device Information Model'::Configurations::Specifications::UpperLimit;
                part nominal [0..1] : 'Device Information Model'::Configurations::Specifications::Nominal;
                part lowerLimit [0..1] : 'Device Information Model'::Configurations::Specifications::LowerLimit;
            }
            connection def Nominal {
                end nominal : 'Device Information Model'::Configurations::Specifications::Nominal => target.nominal;
                end : ControlLimits;
            }
            connection def Nominal {
                end nominal : 'Device Information Model'::Configurations::Specifications::Nominal => target.nominal;
                end : SpecificationLimits;
            }
            connection def UpperLimit {
                end upperLimit : 'Device Information Model'::Configurations::Specifications::UpperLimit => target.upperLimit;
                end : SpecificationLimits;
            }
            connection def LowerLimit {
                end lowerLimit : 'Device Information Model'::Configurations::Specifications::LowerLimit => target.lowerLimit;
                end : AlarmLimits;
            }
            connection def UpperWarning {
                end upperWarning : 'Device Information Model'::Configurations::Specifications::UpperWarning => target.upperWarning;
                end : AlarmLimits;
            }
            connection def LowerLimit {
                end lowerLimit : 'Device Information Model'::Configurations::Specifications::LowerLimit => target.lowerLimit;
                end : ControlLimits;
            }
            connection def LowerLimit {
                end lowerLimit : 'Device Information Model'::Configurations::Specifications::LowerLimit => target.lowerLimit;
                end : SpecificationLimits;
            }
            connection def UpperWarning {
                end upperWarning : 'Device Information Model'::Configurations::Specifications::UpperWarning => target.upperWarning;
                end : ControlLimits;
            }
            connection def LowerWarning {
                end lowerWarning : 'Device Information Model'::Configurations::Specifications::LowerWarning => target.lowerWarning;
                end : AlarmLimits;
            }
            connection def UpperLimit {
                end upperLimit : 'Device Information Model'::Configurations::Specifications::UpperLimit => target.upperLimit;
                end : AlarmLimits;
            }
            connection def LowerWarning {
                end lowerWarning : 'Device Information Model'::Configurations::Specifications::LowerWarning => target.lowerWarning;
                end : ControlLimits;
            }
            connection def UpperLimit {
                end upperLimit : 'Device Information Model'::Configurations::Specifications::UpperLimit => target.upperLimit;
                end : ControlLimits;
            }
            part def UpperWarning {
                doc /* upper boundary indicating increased concern and supervision may be required.*/
                attribute value [1] : Profile::DataTypes::float;
            }
            part def UpperLimit {
                doc 
                /* upper conformance boundary for a variable.
                 *
                 * > Note: immediate concern or action may be required.*/
                attribute value [1] : Profile::DataTypes::float;
            }
            part def Maximum {
                doc /* numeric upper constraint.*/
                attribute value [1] : Profile::DataTypes::float;
            }
            part def LowerLimit {
                doc 
                /* lower conformance boundary for a variable.
                 *
                 * > Note: immediate concern or action may be required.*/
                attribute value [1] : Profile::DataTypes::float;
            }
            part def LowerWarning {
                doc /* lower boundary indicating increased concern and supervision may be required.*/
                attribute value [1] : Profile::DataTypes::float;
            }
            part def Minimum {
                doc /* numeric lower constraint.*/
                attribute value [1] : Profile::DataTypes::float;
            }
            part def Nominal {
                doc /* numeric target or expected value.*/
                attribute value [1] : Profile::DataTypes::float;
            }
            connection def SpecificationLimits {
                end hasSpecificationLimits : SpecificationLimits => target.hasSpecificationLimits;
                doc /* See {{sect(SpecificationLimits)}}.*/
                private end : ProcessSpecification;
            }
            connection def ControlLimits {
                end hasControlLimits : ControlLimits => target.hasControlLimits;
                doc /* See {{sect(ControlLimits)}}.*/
                private end : ProcessSpecification;
            }
            connection def AlarmLimits {
                end hasAlarmLimits : AlarmLimits => target.hasAlarmLimits;
                doc /* See {{sect(AlarmLimits)}}.*/
                private end : ProcessSpecification;
            }
            connection def Maximum {
                end hasMaximum : Maximum => target.hasMaximum;
                private end : Specification;
            }
            connection def UpperLimit {
                end hasUpperLimit : 'Device Information Model'::Configurations::Specifications::UpperLimit => target.hasUpperLimit;
                private end : Specification;
            }
            connection def LowerWarning {
                end hasLowerWarning : 'Device Information Model'::Configurations::Specifications::LowerWarning => target.hasLowerWarning;
                private end : Specification;
            }
            connection def LowerLimit {
                end hasLowerLimit : 'Device Information Model'::Configurations::Specifications::LowerLimit => target.hasLowerLimit;
                private end : Specification;
            }
            connection def UpperWarning {
                end hasUpperWarning : 'Device Information Model'::Configurations::Specifications::UpperWarning => target.hasUpperWarning;
                private end : Specification;
            }
            connection def Nominal {
                end hasNominal : 'Device Information Model'::Configurations::Specifications::Nominal => target.hasNominal;
                private end : Specification;
            }
            connection def Minimum {
                end hasMinimum : Minimum => target.hasMinimum;
                private end : Specification;
            }
            doc 
            /* This section provides semantic information for the {{block(Specification)}} entity.
             *
             * ![Specifications](figures/Specifications.png "Specifications"){: width="0.8"}
             *
             * > Note: See {{sect(Configuration Schema Diagrams)}} for XML schema.
             *
             * ![Specification Example](figures/Specification%20Example.png "Specification Example"){: width="0.8"}
             *
             * > Note: See {{lst(specification-example)}} for the {{term(XML)}} representation of the same example.*/
        }
        package Sensor {
            connection def Channels {
                end hasChannel : Channel => isChannelOf.hasChannel;
                end isChannelOf : SensorConfiguration => hasChannel.'Device Information Model'::Configurations::Sensor::Channel::isChannelOf;
                doc /* {{block(Channels)}} groups one or more {{block(Channel)}} entities. See {{block(Channel)}}.*/
            }
            part def SensorConfiguration {
                doc /* configuration for a {{block(Sensor)}}.*/
                comment /* Description*/
                attribute CalibrationDate [0..1] : Profile::DataTypes::datetime {
                    doc /* Date upon which the {{term(sensor unit)}} was last calibrated.*/
                }
                attribute CalibrationInitials [0..1] : Profile::DataTypes::string {
                    doc /* The initials of the person verifying the validity of the calibration data.*/
                }
                attribute FirmwareVersion [1] : Profile::DataTypes::string {
                    doc /* Version number for the sensor unit as specified by the manufacturer.*/
                }
                attribute NextCalibrationDate [0..1] : Profile::DataTypes::datetime {
                    doc /* Date upon which the {{term(sensor unit)}} is next scheduled to be calibrated.*/
                }
                part hasChannel [0..*] : Channel;
                doc 
                /* ![SensorConfiguration](figures/SensorConfiguration.png "SensorConfiguration"){: width="0.8"}
                 *
                 * > Note: See {{sect(Configuration Schema Diagrams)}} for XML schema.*/
            }
            part def Channel {
                doc /* {{term(sensing element)}} of a {{block(Sensor)}}.*/
                comment /* Description*/
                attribute CalibrationDate [0..1] : Profile::DataTypes::datetime {
                    doc /* Date upon which the {{term(sensor unit)}} was last calibrated to the {{term(sensor element)}}.*/
                }
                attribute CalibrationInitials [0..1] : Profile::DataTypes::string {
                    doc /* The initials of the person verifying the validity of the calibration data.*/
                }
                attribute name [0..1] : Profile::DataTypes::string {
                    doc /* name of the specific {{term(sensing element)}}.*/
                }
                attribute NextCalibrationDate [0..1] : Profile::DataTypes::datetime {
                    doc /* Date upon which the {{term(sensor element)}} is next scheduled to be calibrated with the {{term(sensor unit)}}.*/
                }
                attribute number [1] : Profile::DataTypes::string {
                    doc /* unique identifier that will only refer to a specific {{term(sensing element)}}.*/
                }
                private ref part isChannelOf : SensorConfiguration;
                private attribute Description [0..1] : Profile::DataTypes::string {
                    doc /* textual description for {{block(Channel)}}.*/
                }
                doc /* When {{block(Sensor)}} has multiple {{termplural(sensing element)}}, each {{term(sensing element)}} is modeled as a {{block(Channel)}} for the {{block(Sensor)}}. */
            }
            doc 
            /* This section provides semantic information for the {{block(SensorConfiguration)}} entity.
             *
             * {{term(sensor)}} is a unique type of a piece of equipment.  A {{term(sensor)}} is typically comprised of two major components: a {{term(sensor unit)}} that provides signal processing, conversion, and communications and the {{termplural(sensing element)}} that provides a signal or measured value.
             *
             * The {{term(sensor unit)}} is modeled as a {{term(lower level)}} {{block(Component)}} called {{block(Sensor)}}.  The {{term(sensing element)}} may be modeled as a {{block(Composition)}} element of a {{block(Sensor)}} element and the measured value would be modeled as a {{block(DataItem)}} (See {{sect(DataItems)}} for more information on {{block(DataItem)}} elements).  Each {{term(sensor unit)}} may have multiple {{termplural(sensing element)}}; each representing the data for a variety of measured values.
             *
             * ![Sensing Element provided as a DataItem Example](figures/Sensing%20Element%20provided%20as%20a%20DataItem%20Example.png "Sensing Element provided as a DataItem Example"){: width="0.8"}
             *
             * > Note: See {{lst(example-of-sensing-element-provided-as-data-item-associated-with-a-component)}} for an {{term(XML)}} example.
             *
             * When a {{term(sensor unit)}} is modeled as a {{block(Component)}} or as a separate piece of equipment, it may provide additional configuration information for the {{termplural(sensor element)}} and the {{term(sensor unit)}} itself.  
             *
             * ![Sensor for Rotary Axis Example](figures/Sensor%20for%20Rotary%20Axis%20Example.png "Sensor for Rotary Axis Example"){: width="0.8"}
             *
             * > Note: If a {{block(Sensor)}} provides vibration measurement data for the spindle on a piece of equipment, it could be modeled as a {{block(Sensor)}} for rotary axis named `C`. See {{lst(example-of-sensor-for-rotary-axis)}} for an {{term(XML)}} example.
             *
             * ![Sensor unit with Sensing Elements Example](figures/Sensor%20unit%20with%20Sensing%20Elements%20Example.png "Sensor unit with Sensing Elements Example"){: width="0.8"}
             *
             * > Note: If a {{block(Sensor)}} provides measurement data for multiple {{block(Component)}} elements within a piece of equipment and is not associated with any particular {{block(Component)}}, it **MAY** be modeled as an independent {{block(Component)}} and the data associated with measurements are associated with their associated {{block(Component)}} entities. See {{lst(example-of-sensor-unit-with-sensing-element)}} for an {{term(XML)}} example.
             *
             * {{block(Configuration)}} data provides information required for maintenance and support of the sensor.
             *
             * When {{block(Sensor)}} represents the {{term(sensor unit)}} for multiple {{term(sensing element)}}(s), each sensing element is represented by a {{block(Channel)}}.   The {{term(sensor unit)}} itself and each {{block(Channel)}} representing one {{term(sensing element)}} **MAY** have its own configuration data.
             *
             * ![Sensor Configuration Example](figures/Sensor%20Configuration%20Example.png "Sensor Configuration Example"){: width="0.8"}
             *
             * > Note: See {{lst(example-of-configuration-data-for-sensor)}} for an {{term(XML)}} example.
             */
        }
        package Relationships {
            abstract part def ConfigurationRelationship {
                doc /* association between two pieces of equipment or assets that may function independently but together perform a manufacturing operation.*/
                comment /* Description*/
                attribute name [0..1] : Profile::DataTypes::string {
                    doc /* name associated with this {{block(ConfigurationRelationship)}}.*/
                }
                attribute id [1] : Profile::DataTypes::ID {
                    doc /* unique identifier for this {{block(ConfigurationRelationship)}}.*/
                }
                attribute type [1] : Profile::DataTypes::RelationshipTypeEnum {
                    doc /* defines the authority that this piece of equipment has relative to the associated piece of equipment.*/
                }
                attribute criticality [0..1] : Profile::DataTypes::CriticalityTypeEnum {
                    doc /* defines whether the services or functions provided by the associated piece of equipment is required for the operation of this piece of equipment.*/
                }
                doc /* {{block(ConfigurationRelationship)}} is an abstract entity and hence will be realized by specific {{block(ConfigurationRelationship)}} types in an {{block(MTConnectDevices)}} entity. See {{sect(ComponentRelationship)}} and {{sect(DeviceRelationship)}}.*/
            }
            part def ComponentRelationship :> ConfigurationRelationship {
                doc /* {{block(ConfigurationRelationship)}} that describes the association between a {{block(Component)}} or an {{block(Asset)}} and another {{block(Component)}}.*/
                attribute idRef [1] : Profile::DataTypes::ID {
                    doc /* reference to the associated {{block(Component)}}.*/
                }
            }
            part def DeviceRelationship :> ConfigurationRelationship {
                doc /* {{block(ConfigurationRelationship)}} that describes the association between a {{block(Component)}} or an {{block(Asset)}} and a {{block(Device)}}.*/
                attribute deviceUuidRef [1] : Profile::DataTypes::UUID {
                    doc /* reference to the {{property(Device::uuid)}} of the associated piece of equipment.*/
                }
                attribute href [0..1] : Profile::DataTypes::xlinkhref {
                    doc /* {{term(URI)}} identifying the {{term(agent)}} that is publishing information for the associated piece of equipment. */
                    comment /* Description*/
                    doc 
                    /* {{property(DeviceRelationship::href)}} **MUST** also include the {{property(Device::uuid)}} for that specific piece of equipment.
                     *
                     * {{property(href)}} is of type `xlink:href` from the W3C XLink specification: {{cite(https://www.w3.org/TR/xlink11/)}}.*/
                }
                attribute role [0..1] : Profile::DataTypes::RoleTypeEnum {
                    doc /* defines the services or capabilities that the referenced piece of equipment provides relative to this piece of equipment.*/
                }
                attribute 'xlink:type' [0..1] : Profile::DataTypes::xlinktype {
                    doc /* `xlink:type`**MUST** have a fixed value of `locator` as defined in W3C XLink 1.1 {{cite(https://www.w3.org/TR/xlink11/)}}.*/
                    comment /* Description*/
                    doc /* If the {{property(DeviceRelationship::href)}} is provided, it **MUST** conform to the {{term(URI)}} syntactic rules as defined in IETF RFC 3986 for Uniform Resource Identifiers. {{cite(https://www.ietf.org/rfc/rfc3986.txt)}}*/
                }
            }
            part def AssetRelationship :> ConfigurationRelationship {
                doc /* {{block(ConfigurationRelationship)}} that describes the association between a {{block(Component)}} or an {{block(Asset)}} and another {{block(Asset)}}.*/
                attribute assetIdRef [1] : Profile::DataTypes::ID {
                    doc /* uuid of the related {{block(Asset)}}.*/
                }
                attribute assetType [1] : Profile::DataTypes::string {
                    doc /* type of {{block(Asset)}} being referenced.*/
                }
                attribute href [0..1] : Profile::DataTypes::xlinkhref {
                    doc /* {{term(URI)}} reference to the associated {{block(Asset)}}.*/
                    comment /* Description*/
                    doc 
                    /* {{property(AssetRelationship::href)}} **MUST** also include the {{property(Device::uuid)}} for that specific piece of equipment.
                     *
                     * {{property(AssetRelationship::href)}} is of type `xlink:href` from the W3C XLink specification: {{cite(https://www.w3.org/TR/xlink11/)}}.*/
                }
            }
            doc 
            /* This section provides semantic information for the {{block(ConfigurationRelationship)}} entity.
             *
             * ![Relationships](figures/Relationships.png "Relationships"){: width="0.8"}
             *
             * > Note: See {{sect(Configuration Schema Diagrams)}} for XML schema.
             *
             * ![Relationship Example](figures/Relationship%20Example.png "Relationship Example"){: width="0.8"}
             *
             * > Note: See {{lst(relationship-example)}} for the {{term(XML)}} representation of the same example.*/
        }
        part def Configuration :> Glossary::'MTConnect Terms'::Configuration {
            doc /* technical information about an entity describing its physical layout, functional characteristics, and relationships with other entities.*/
            private ref part isConfigurationFor : Components::Component;
            part hasSolidModel [0..1] : SolidModel::SolidModel;
            part hasSensorConfiguration [0..1] : Sensor::SensorConfiguration;
            part hasMotion [0..1] : Motion::Motion;
            part hasRelationship [0..*] : Relationships::ConfigurationRelationship;
            part hasCoordinateSystem [0..*] : CoordinateSystems::CoordinateSystem;
            part hasSpecification [0..*] : Specifications::Specification;
            private ref part isConfigurationFor : Compositions::Composition;
            part hasImageFile [0..*] : 'Device Information Model'::Configurations::ImageFiles::ImageFile;
            part hasPowerSource [0..*] : 'Device Information Model'::Configurations::PowerSources::PowerSource;
        }
        package SolidModel {
            part def SolidModel {
                doc /* references to a file with the three-dimensional geometry of the {{block(Component)}} or {{block(Composition)}}.*/
                comment /* Description*/
                attribute id [1] : Profile::DataTypes::ID {
                    doc /* unique identifier for this element.*/
                }
                part hasTransformation [0..1] : CoordinateSystems::Transformation;
                part hasScale [0..1] : AbstractScale;
                attribute solidModelIdRef [0..1] : Profile::DataTypes::ID {
                    doc /* associated model file if an item reference is used.*/
                }
                attribute href [0..1] : Profile::DataTypes::string {
                    doc 
                    /* {{term(URL)}} giving the location of the {{block(SolidModel)}}. 
                     *
                     * If not present, the model referenced in the {{property(SolidModel::solidModelIdRef)}} is used.
                     *
                     * {{property(SolidModel::href)}} is of type `xlink:href` from the W3C XLink specification.*/
                }
                attribute itemRef [0..1] : Profile::DataTypes::string {
                    doc 
                    /* reference to the item within the model within the related geometry. A {{property(SolidModel::solidModelIdRef)}} **MUST** be given. 
                     *
                     * > Note: `Item` defined in ASME Y14.100 - A nonspecific term used to denote any unit or product, including materials, parts, assemblies, equipment, accessories, and computer software.*/
                }
                attribute mediaType [1] : Profile::DataTypes::MediaTypeEnum {
                    doc /* format of the referenced document.*/
                }
                attribute coordinateSystemIdRef [0..1] : Profile::DataTypes::ID {
                    doc /* reference to the coordinate system for this {{block(SolidModel)}}.*/
                }
                attribute nativeUnits [0..1] : Profile::DataTypes::NativeUnitEnum {
                    doc /* same as {{property(DataItem::nativeUnits)}}. See {{sect(DataItem)}}.*/
                }
                attribute units [0..1] : Profile::DataTypes::UnitEnum {
                    doc /* same as {{property(DataItem::units)}}. See {{sect(DataItem)}}.*/
                }
                doc 
                /* The geometry **MAY** have a transformation and a scale to position the {{block(Component)}} with respect to the other {{block(Component)}}s. A geometry file can contain a set of assembled items, in this case, the {{block(SolidModel)}} references the {{property(SolidModel::id)}} of the assembly model file and the specific item within that file.
                 *
                 * The {{block(SolidModel)}} **MAY** provide a translation, rotation, and scale to correctly place it relative to the other geometries in the machine. If the {{block(Component)}} can move and has a {{block(Motion)}} {{block(Configuration)}}, the {{block(SolidModel)}} will move when the {{block(Component)}} or {{block(Composition)}} moves.
                 *
                 * Either an {{property(SolidModel::href)}} or a {{property(SolidModel::modelIdRef)}} and an {{property(SolidModel::itemRef)}} **MUST** be specified.*/
            }
            connection def Transformation {
                end hasTransformation : CoordinateSystems::Transformation => target.hasTransformation;
                doc /* See {{sect(Transformation)}}.*/
                end : Configurations::SolidModel::SolidModel;
            }
            abstract part def AbstractScale {
                doc /* either a single multiplier applied to all three dimensions or a three space multiplier given in the X, Y, and Z dimensions in the coordinate system used for the {{block(SolidModel)}}.*/
            }
            connection def Scale {
                end hasScale : AbstractScale => target.hasScale;
                doc /* See {{sect(Scale)}}.*/
                end : Configurations::SolidModel::SolidModel;
            }
            part def ScaleDataSet :> 'Observation Information Model'::Representations::DataSet, AbstractScale {
                doc /* either a single multiplier applied to all three dimensions or a three space multiplier given in the X, Y, and Z dimensions in the coordinate system used for the {{block(SolidModel)}} represented as a dataset.*/
                attribute X [0..1] : Profile::DataTypes::float {
                    doc /* multiplier for X axis.*/
                }
                attribute Y [0..1] : Profile::DataTypes::float {
                    doc /* multiplier for Y axis.*/
                }
                attribute Z [0..1] : Profile::DataTypes::float {
                    doc /* multiplier for Z axis.*/
                }
            }
            part def Scale :> AbstractScale {
                doc /* either a single multiplier applied to all three dimensions or a three space multiplier given in the X, Y, and Z dimensions in the coordinate system used for the {{block(SolidModel)}}.*/
                private attribute value [0..1] : Profile::DataTypes::float3d;
            }
            doc 
            /* This section provides semantic information for the {{block(SolidModel)}} entity.
             *
             * ![SolidModel](figures/SolidModel.png "SolidModel"){: width="0.8"}
             *
             * > Note: See {{sect(Configuration Schema Diagrams)}} for XML schema.
             *
             * ![SolidModel Example](figures/SolidModel%20Example.png "SolidModel Example"){: width="0.8"}
             *
             * > Note: See {{lst(solidmodel-example)}} for the {{term(XML)}} representation of the same example.*/
        }
        connection def SolidModel {
            end hasSolidModel : SolidModel::SolidModel => target.hasSolidModel;
            doc /* See {{sect(SolidModel)}}.*/
            private end : Configuration;
        }
        connection def SensorConfiguration {
            end hasSensorConfiguration : Sensor::SensorConfiguration => target.hasSensorConfiguration;
            doc /* See {{block(SensorConfiguration)}}.*/
            private end : Configuration;
        }
        connection def Motion {
            end hasMotion : Motion::Motion => target.hasMotion;
            doc /* See {{sect(Motion)}}.*/
            private end : Configuration;
        }
        connection def Relationships {
            end hasRelationship : Relationships::ConfigurationRelationship => target.hasRelationship;
            doc /* {{block(Relationships)}} groups one or more {{block(ConfigurationRelationship)}} types. See {{package(Relationships)}}.*/
            private end : Configuration;
        }
        connection def CoordinateSystems {
            end hasCoordinateSystem : CoordinateSystems::CoordinateSystem => target.hasCoordinateSystem;
            doc /* {{block(CoordinateSystems)}} groups one or more {{block(CoordinateSystem)}} entities. See {{package(CoordinateSystems)}}.*/
            private end : Configuration;
        }
        connection def Specifications {
            end hasSpecification : Specifications::Specification => target.hasSpecification;
            doc /* {{block(Specifications)}} groups one or more {{block(Specification)}} entities. See {{package(Specifications)}}.*/
            private end : Configuration;
        }
        connection def ImageFiles {
            end hasImageFile : 'Device Information Model'::Configurations::ImageFiles::ImageFile => target.hasImageFile;
            doc /* {{block(ImageFiles)}} groups one or more {{block(ImageFile)}} entities. See {{package(ImageFiles)}}.*/
            private end : Configuration;
        }
        package ImageFiles {
            part def ImageFile {
                doc /* reference to a file containing an image of the {{block(Component)}}.*/
                attribute id [1] : Profile::DataTypes::ID {
                    doc /* unique identifier of the image file.*/
                }
                attribute href [1] : Profile::DataTypes::string {
                    doc /* {{term(URL)}} giving the location of the image file.*/
                }
                attribute mediaType [1] : Profile::DataTypes::string {
                    doc /* mime type of the image file.*/
                }
                attribute name [0..1] : Profile::DataTypes::string {
                    doc /* description of the image file.*/
                }
            }
            doc /* This section provides semantic information for the {{block(ImageFile)}} entity.*/
        }
        connection def PowerSources {
            end hasPowerSource : 'Device Information Model'::Configurations::PowerSources::PowerSource => target.hasPowerSource;
            doc /* {{block(PowerSources)}} groups one or more {{block(PowerSource)}} entities. See {{package(PowerSources)}}.*/
            private end : Configuration;
        }
        package PowerSources {
            part def PowerSource {
                doc /* potential energy sources for the {{block(Component)}}.*/
                attribute type [1] : Profile::DataTypes::PowerSourceTypeEnum {
                    doc /* type of the power source.*/
                }
                attribute id [1] : Profile::DataTypes::ID {
                    doc /* unique identifier for the power source.*/
                }
                attribute componentIdRef [0..1] : Profile::DataTypes::ID {
                    doc /* reference to the {{block(Component)}} providing observations about the power source.*/
                }
                attribute order [0..1] : Profile::DataTypes::integer {
                    doc /* optional precedence for a given power source.*/
                }
                attribute value [1] : Profile::DataTypes::string {
                    doc /* name of the power source.*/
                }
            }
            doc 
            /* This section provides semantic information for the {{block(PowerSource)}} entity.
             *
             * ![PowerSources](figures/PowerSources.png "PowerSources"){: width="0.8"}
             *
             */
        }
        doc 
        /* {{figure(Configuration)}} shows the abstract {{block(Configuration)}} and its types.
         *
         * ![Configuration](figures/Configuration.png "Configuration"){: width="0.8"}
         *
         * > Note: See {{sect(Configuration Schema Diagrams)}} for XML schema.*/
        comment /* Configurations Model*/
        doc /* This section provides semantic information for the {{block(Configuration)}} entity that is used to model technical information about a {{block(Component)}}. */
    }
    part def Device :> Components::Component, Glossary::'MTConnect Terms'::Device {
        doc /* {{block(Component)}} composed of a piece of equipment that produces {{termplural(observation)}} about itself.*/
        comment /* Description*/
        part hasAuxiliary [0..*] : Components::'Component Types'::Auxiliary;
        part hasController [0..*] : Components::'Component Types'::Controller;
        part hasInterface [0..*] : 'Interface Interaction Model'::Interface;
        part hasResource [0..*] : Components::'Component Types'::Resource;
        part hasStructure [0..*] : Components::'Component Types'::Structure;
        attribute iso841Class [0..1] : Profile::DataTypes::string {
            doc /* **DEPRECATED** in *MTConnect Version 1.2*.*/
        }
        attribute uuid [1] :>> uuid : Profile::DataTypes::UUID {
            doc /* universally unique identifier for the element.*/
        }
        attribute mtconnectVersion [0..1] : Profile::DataTypes::string {
            doc /* MTConnect version of the {{term(Device Information Model)}} used to configure the information to be published for a piece of equipment in an {{term(MTConnect Response Document)}}.*/
        }
        part hasSystem [0..*] : Components::'Component Types'::System;
        attribute name [1] :>> name : Profile::DataTypes::string {
            doc /* name of an element or a piece of equipment.*/
        }
        private part hasPart [0..*] : Components::'Component Types'::Part;
        private part hasProcess [0..*] : Components::'Component Types'::Process;
        part hasAxis [0..*] : Components::'Component Types'::Axis;
        part hasAdapter [0..*] : Components::'Component Types'::Adapter;
        part observesAvailability [1] : 'Observation Information Model'::'Observation Types'::'Event Types'::Availability;
        part observesAssetChanged [1] : 'Observation Information Model'::'Observation Types'::'Event Types'::AssetChanged;
        part observesAssetRemoved [1] : 'Observation Information Model'::'Observation Types'::'Event Types'::AssetRemoved;
        attribute hash [0..1] : Profile::DataTypes::string {
            doc /* condensed message digest from a secure one-way hash function. {{cite(FIPS PUB 180-4)}}*/
        }
        state def Device {
            state INACTIVE;
            state COMMITTED;
            state PREPARING;
        }
        doc 
        /* A {{block(Device)}} {{termplural(organize)}} its parts as {{block(Component)}} entities.
         *
         * A {{block(Device)}} **MUST** have a {{property(Device::name)}} and {{property(Device::uuid)}} to identify itself. 
         *
         * A {{block(Device)}} **MUST** have the following {{block(DataItems)}}: {{block(Availability)}}, {{block(AssetChanged)}}, and {{block(AssetRemoved)}}.
         *
         * See {{package(Components)}} for more details on the properties of {{block(Device)}}.
         *
         * > See {{sect(Part Properties of Device)}} for a list of {{term(top level)}} {{block(Component)}} types for a {{block(Device)}}.
         */
        exhibit state : Device;
    }
    connection def {
        end observesAvailability : 'Observation Information Model'::'Observation Types'::'Event Types'::Availability => target.observesAvailability;
        private end : Device;
    }
    connection def {
        end observesAssetChanged : 'Observation Information Model'::'Observation Types'::'Event Types'::AssetChanged => target.observesAssetChanged;
        private end : Device;
    }
    connection def {
        end observesAssetRemoved : 'Observation Information Model'::'Observation Types'::'Event Types'::AssetRemoved => target.observesAssetRemoved;
        private end : Device;
    }
    doc 
    /* The {{term(Device Information Model)}} provides a representation of the physical and logical configuration for a piece of equipment used for a manufacturing process or for any other purpose.  It also provides the definition of data that may be reported by that equipment. 
     *
     * Using information defined in the {{term(Device Information Model)}}, a software application can determine the configuration and reporting capabilities of a piece of equipment.  To do this, the software application issues a {{term(probe request)}} (defined in {{package(Fundamentals)}}) to an {{term(agent)}} associated with a piece of equipment. An {{term(agent)}} responds to the {{term(probe request)}} with an {{term(MTConnectDevices Response Document)}} that contains information describing both the physical and logical structure of the piece of equipment and a detailed description of each {{term(Observation)}} that can be reported by the {{term(agent)}} associated with the piece of equipment. This information allows the client software application to interpret the document and to extract the data with the same meaning, value, and context that it had at its original source.  
     *
     * The {{term(MTConnectDevices Response Document)}} is comprised of two sections: {{block(Header)}} and {{block(Devices)}}.
     *
     * The {{block(Header)}} section contains protocol related information as defined in {{package(Fundamentals)}}.
     *
     * The {{block(Devices)}} section of the {{term(MTConnectDevices Response Document)}} contains a {{block(Device)}} entity for each piece of equipment described in the document.  Each {{block(Device)}} is comprised of two primary types of entities - {{termplural(Component)}} and {{termplural(DataItem)}}.  
     *
     * {{termplural(Component)}} organize information that represents the physical and logical parts and sub-parts of a piece of equipment (See {{package(Components)}} for more details).  
     *
     * {{termplural(DataItem)}} describe data that can be reported by a piece of equipment.  In the {{term(Device Information Model)}}, {{termplural(DataItem)}} are defined as {{block(DataItem)}} entities (See {{package(DataItem Types)}}).
     *
     * The {{termplural(Component)}} and {{termplural(DataItem)}} in the {{term(MTConnectDevices Response Document)}} provide information representing the physical and logical structure for a piece of equipment and the types of data that the piece of equipment can report relative to that structure.   The {{term(MTConnectDevices Response Document)}} does not contain values for the data types reported by the piece of equipment.  The {{term(MTConnectStreams Response Document)}} defined in {{package(Observation Information Model)}} provides the data values that are reported by the piece of equipment.
     *
     * > Note:  The MTConnect Standard also defines the information model for {{termplural(asset)}}.  An {{term(asset)}} is something that is used in the manufacturing process, but is not permanently associated with a single piece of equipment, can be removed from the piece of equipment without compromising its function, and can be associated with other pieces of equipment during its lifecycle.  See {{package(Asset Information Model)}} for more details on {{termplural(asset)}}.
     */
    comment /* Devices Appendix*/
    doc 
    /* {{newpage()}} 
     *
     * ## XML Schema Diagrams
     *
     * See XML schemas for the MTConnect standard here: {{url(https://schemas.mtconnect.org/)}}.
     *
     * ### Components Schema Diagrams
     *
     * See `Components` element in `MTConnectDevices` schema.
     *
     * See `Description` element in `MTConnectDevices` schema.
     *
     * ### DataItems Schema Diagrams
     *
     * See `DataItems` element in `MTConnectDevices` schema.
     *
     * See `Source` element in `MTConnectDevices` schema.
     *
     * See `Constraints` element in `MTConnectDevices` schema.
     *
     * See `Filter` element in `MTConnectDevices` schema.
     *
     * See `Definition` element in `MTConnectDevices` schema.
     *
     * ### References Schema Diagrams
     *
     * See `References` element in `MTConnectDevices` schema.
     *
     * See `ComponentRef` element in `MTConnectDevices` schema.
     *
     * See `DataItemRef` element in `MTConnectDevices` schema.
     *
     * ### Configuration Schema Diagrams
     *
     * See `Configuration` element in `MTConnectDevices` schema.
     *
     * See `CoordinateSystem` element in `MTConnectDevices` schema.
     *
     * See `Motion` element in `MTConnectDevices` schema.
     *
     * See `Relationships` element in `MTConnectDevices` schema.
     *
     * See `ComponentRelationship` element in `MTConnectDevices` schema.
     *
     * See `DeviceRelationship` element in `MTConnectDevices` schema.
     *
     * See `SensorConfiguration` element in `MTConnectDevices` schema.
     *
     * See `SolidModel` element in `MTConnectDevices` schema.
     *
     * See `Specifications` element in `MTConnectDevices` schema.
     *
     * See `ProcessSpecification` element in `MTConnectDevices` schema.
     *
     * ## XML Examples
     *
     * ### Device Entity Hierarchy Example
     *
     * ~~~~xml
     * <Devices>
     *   <Device id="d1" name="M12346" uuid="M80104K162N">
     *     <Components>
     *     <Axes id="a" name="base">
     *     <Components>
     *       <Linear id="x" name="X"/>
     *       <Linear id="y" name="Y"/>
     *       <Linear id="z" name="Z"/>
     *       <Rotary id="ar" name="B"/>
     *       <Linear id="w" name="Z3" nativeName="W"/>
     *       <Rotary id="c" name="C"/>
     *     </Components>
     *     </Axes>
     *     <Controller id="cont" name="controller">
     *     <Components>
     *       <Path id="path1" name="path"/>
     *     </Components>
     *     </Controller>
     *     <Door id="door1" name="door"/>
     *     <Systems id="systems" name="systems">
     *     <Components>
     *       <WorkEnvelope id="we1" name="workenv">
     *       <Compositions>
     *         <Composition type="WORKPIECE" id="wp"/>
     *         <Composition type="TABLE" id="tbl"/>
     *       </Compositions>
     *       </WorkEnvelope>
     *       <Electric id="elec" name="electric"/>
     *       <Hydraulic id="hydraulic" name="hydraulic"/>
     *       <Coolant id="coolant" name="coolant"/>
     *       <Pneumatic id="pneumatic" name="pneumatic"/>
     *       <Lubrication id="lubrication" name="lubrication"/>
     *     </Components>
     *     </Systems>
     *     <Auxiliaries id="Aux" name="auxiliaries">
     *     <Components>
     *       <Environmental id="room" name="environmental"/>
     *     </Components>
     *     </Auxiliaries>
     *     <Resources id="resources" name="resources">
     *     <Components>
     *       <Personnel id="personnel" name="personnel"/>
     *       <Materials id="materials" name="materials">
     *       <Components>
     *         <Stock id="procstock" name="stock"/>
     *       </Components>
     *       <Materials/>
     *     </Components> 
     *     </Resources>
     *     </Components>
     *   </Device>
     * </Devices>
     * ~~~~
     * {: caption="Device Entity Hierarchy Example"}
     *
     * ### Component Example
     *
     * ~~~~xml
     * <Devices>
     *   <Device id="d1" name="M12346" uuid="M80104K162N">
     *     <Description manufacturer="Example_Corporation" 
     *       serialNumber="272237"> Mill w/SMooth-G
     *     </Description>
     *   <DataItems>
     *     <DataItem category="EVENT" id="avail" name="avail" type="AVAILABILITY"/>
     *     <DataItem category="EVENT" id="d1_asset_chg" name="asset_chg" type="ASSET_CHANGED"/>
     *     <DataItem category="EVENT" id="d1_asset_rem" name="asset_rem" type="ASSET_REMOVED"/>
     *   </DataItems>
     *     <Components>
     *     <Controller id="cont" name="controller">
     *       <DataItems>
     *       <DataItem category="EVENT" id="estop" name="estop" type="EMERGENCY_STOP"/>
     *       <DataItem category="CONDITION" id="logic_cond" type="LOGIC_PROGRAM"/>
     *       <DataItem category="CONDITION" id="cont_system" type="SYSTEM"/>
     *       <DataItem category="SAMPLE" id="cut_time" type="ACCUMULATED_TIME" units="SECOND"/>
     *     </DataItems>
     *     <Components>
     *       <Path id="path1" name="path">
     *         <DataItems>
     *         <DataItem category="EVENT" id="execution" name="execution" type="EXECUTION"/>
     *         <DataItem category="SAMPLE" id="cspeed" subType="ACTUAL" type="CUTTING_SPEED" units="MILLIMETER/SECOND"/>
     *         <DataItem category="CONDITION" id="path_system" type="SYSTEM"/>
     *         <DataItem category="EVENT" id="cvars" representation="DATA_SET" type="VARIABLE"/>
     *         <DataItem category="EVENT" id="woffset" representation="TABLE" type="WORK_OFFSET"/>
     *       </DataItems>
     *       </Path>
     *     </Components>
     *     </Controller>
     *   </Components>
     *   </Device>
     * </Devices>
     * ~~~~
     * {: caption="Component Example"}
     *
     * ### Component with Compositions Example
     *
     * In {{term(XML)}}, `Composition` types are represented differently than `Component` types. For `Component` types, the element name is Pascal Case of the `Component` type name. Whereas, the element name for all `Composition`types is `Composition` and the type is defined by the `type` attribute of the element (see example below).
     *
     * ~~~~xml
     * <WorkEnvelope id="we1" name="workenv">
     *   <DataItems>
     *     <DataItem category="CONDITION" id="hardware1" name="hardware1" type="HARDWARE"/>
     *   </DataItems>
     *   <Compositions>
     *   <Composition type="WORKPIECE" id="wp"/>
     *   <Composition type="TABLE" id="tbl"/>
     *   </Compositions>
     * </WorkEnvelope>
     * ~~~~
     * {: caption="Component with Compositions Example"}
     *
     * ### CoordinateSystem Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *   </Device>
     * </Devices>
     * ~~~~
     * {: caption="CoordinateSystem Example"}
     *
     * ### Motion Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *     <Components>
     *       <Axes id="a" name="base">
     *         <Components>
     *           <Linear id="x" name="X">
     *             <Configuration>
     *               <Motion id="xmotion" coordinateSystemIdRef="machcoord" type="PRISMATIC" actuation="DIRECT">
     *                 <Transformation>
     *                   <Translaton>300 915 590</Translaton>
     *                   <Rotation>0 0 0</Rotation>
     *                 </Transformation>
     *                 <Axis>1.0 0 0</Axis>
     *               </Motion>
     *             </Configuration>
     *           </Linear>
     *           <DataItems>
     *             <DataItem id="xtravel" type="SYSTEM" category="CONDITION">
     *           </DataItems>
     *         </Components>
     *       </Axes>
     *     </Components>
     *   </Device>
     * </Devices>
     * ~~~~
     * {: caption="Motion Example"}
     *
     * ### Relationship Example
     *
     * ~~~~xml
     * <Components>
     *   <Axes id="a" name="base">
     *     <Components>
     *       <Linear id="x" name="X">
     *         <Configuration>        
     *           <Relationships>
     *             <ComponentRelationship id="xpar" type="PARENT" idRef="we1"/>
     *           </Relationships>
     *         </Configuration>
     *       </Linear>
     *       <DataItems>
     *         <DataItem id="xtravel" type="SYSTEM" category="CONDITION">
     *       </DataItems>
     *     </Components>
     *   </Axes>
     *   <Systems id="systems" name="systems">
     *     <Components>
     *       <WorkEnvelope id="we1" name="workenv">
     *         <Compositions>
     *           <Composition type="WORKPIECE" id="wp"/>
     *           <Composition type="TABLE" id="tbl"/>
     *         </Compositions>
     *         <DataItems>
     *           <DataItem id="we1cond" type="SYSTEM" category="CONDITION">
     *         </DataItems>
     *       </WorkEnvelope>
     *     </Components>
     *   </Systems>
     * </Components>
     * ~~~~
     * {: caption="Relationship Example"}
     *       
     * ### SolidModel Example
     *
     * ~~~~xml
     * <Devices>
     *   <Device id="d1" name="M12346" uuid="M80104K162N">
     *     <Description manufacturer="Example_Corporation" 
     *       serialNumber="272237"> Mill w/SMooth-G
     *     </Description>
     *     <DataItems>
     *       <DataItem id="avail" type="AVAILABILITY" category="EVENT"/>
     *       <DataItem category="EVENT" id="d1_asset_chg" name="asset_chg" type="ASSET_CHANGED"/>
     *       <DataItem category="EVENT" id="d1_asset_rem" name="asset_rem" type="ASSET_REMOVED"/>
     *     </DataItems>
     *     <Configuration>
     *       <CoordinateSystems>
     *         <CoordinateSystem id="base" type="BASE">
     *           <Origin>0 0 0</Origin>
     *         </CoordinateSystem>
     *         <CoordinateSystem id="machcoord" type="MACHINE" parentIdRef="base">
     *           <Transformation>
     *             <Translation>210 275 1430</Translation>
     *             <Rotation>0 0 0</Rotation>
     *           </Transformation>
     *         </CoordinateSystem>
     *         <CoordinateSystem id="workcoord" type="OBJECT" parentIdRef="machcoord">
     *           <Transformation>
     *             <Translation>0 0 0</Translation>
     *             <Rotation>0 0 0</Rotation>
     *           </Transformation>
     *         </CoordinateSystem>
     *       </CoordinateSystems>
     *     </Configuration>
     *     <Components>
     *       <Structures id="struct">
     *         <Configuration>
     *           <SolidModel id="model" mediaType="OBJ" href="/objs/mazak.obj" coordinateSystemIdRef="base">
     *             <Transformation>
     *               <Translation>0 860 0</Translation>
     *               <Rotation>-90 0 0</Rotation>
     *             </Transformation>
     *             <Scale>0.001 0.001 0.001</Scale>
     *           </SolidModel>
     *         </Configuration>
     *         <Components>
     *           <Structure id="xaxis" name="X_AXIS">
     *             <Configuration>
     *               <SolidModel id="x_model" mediaType="OBJ" itemRef="xaxis" solidModelIdRef="model" coordinateSystemIdRef="base"/>
     *             </Configuration>
     *             <DataItems>
     *               <DataItem type="SYSTEM" category="CONDITION" id="struct_cond"/>
     *             </DataItems>
     *           </Structure>
     *         </Components>
     *       </Structures>
     *     </Components>
     *   </Device>
     * </Devices>
     * ~~~~
     * {: caption="SolidModel Example"}
     *
     * ### Specification Example
     *
     * ~~~~xml
     * <Components>
     *   <Axes id="a" name="base">
     *     <Components>
     *       <Linear id="x" name="X">
     *         <Configuration>
     *           <Specifications>
     *             <Specification id="spec001" type="LENGTH" units="MILLIMETER">
     *               <Nominal>650</Nominal>
     *             </Specification>
     *             <Specification id="spec002" type="LINEAR_FORCE" units="NEWTON">
     *               <Maximum>5200</Maximum>
     *               <Minimum>0</Minimum>
     *             </Specification>
     *           </Specifications>
     *         </Configuration>
     *         <DataItems>
     *           <DataItem id="xtravel" type="SYSTEM" category="CONDITION">
     *         </DataItems>
     *       </Linear>
     *     </Components>
     *   </Axes>
     * </Components>
     * ~~~~
     * {: caption="Specification Example"}
     *
     * ### Example of sensing element provided as data item associated with a Component
     *
     * ~~~~xml
     * <Components>
     *   <Axes id="a" name="base"
     *     <Components>
     *       <Rotary id="c" name="C">
     *         <DataItems>
     *           <DataItem type="TEMPERATURE" id="servotemp4"
     *             category="SAMPLE" nativeUnits="CELSIUS"
     *             compositionId="Bmotor" units="CELSIUS"/>
     *           </DataItems>
     *       </Rotary>
     *     </Components>
     *   </Axes>
     * </Components>
     * ~~~~
     * {: caption="Example of sensing element provided as data item associated with a Component"}
     *
     * ### Example of Sensor for rotary axis
     *
     * ~~~~xml
     * <Components>
     *   <Axes id="a" name="base"
     *     <Components>
     *       <Rotary id="ar" name="B">
     *         <Components>
     *           <Sensor id="spdlm" name="Spindlemonitor">
     *             <DataItems>
     *               <DataItem type="DISPLACEMENT" id="cvib"
     *                 category="SAMPLE" name="Svib" 
     *                 units="MILLIMETER"/>
     *             </DataItems>
     *           </Sensor >
     *         <Components>
     *       </Rotary>
     *     </Components>
     *   </Axes>
     * </Components>
     * ~~~~
     * {: caption="Example of Sensor for rotary axis"}
     *
     * ### Example of sensor unit with sensing element
     *
     * ~~~~xml
     * <Axes id="a" name="base"
     *   <Components>
     *   <Sensor id="sens1" name="Sensorunit">
     *     <DataItems>
     *     <DataItem type="TEMPERATURE" id="sentemp"
     *       category="SAMPLE" name="Sensortemp" 
     *       units="CELSIUS"/> 
     *     </DataItems>
     *   </Sensor >
     *   <Linear id="x" name="X">
     *     <DataItems>
     *     <DataItem type="DISPLACEMENT" id="xvib"
     *       category="SAMPLE" name="xvib" 
     *       units="MILLIMETER">
     *       <Source componentId="sens1"/>
     *     </DataItem>
     *     </DataItems>
     *   </Rotary>
     *   <Linear id="y" name="Y">
     *     <DataItems>
     *     <DataItem type="DISPLACEMENT" id="yvib" 
     *       category="SAMPLE" name="yvib" 
     *       units="MILLIMETER">
     *       <Source componentId="sens1"/>
     *     </DataItem>
     *     </DataItems>
     *   </Linear>
     *   <Components>
     * </Axes>
     * ~~~~
     * {: caption="Example of sensor unit with sensing element"}
     *
     * ### Example of configuration data for Sensor
     *
     * ~~~~xml
     * <Sensor id="sensor" name="sensor">
     *   <Configuration>
     *     <SensorConfiguration>
     *       <FirmwareVersion>2.02</FirmwareVersion>
     *       <CalibrationDate>2010-05-16</CalibrationDate>
     *       <NextCalibrationDate>2010-05-16</NextCalibrationDate>
     *       <CalibrationInitials>WS</CalibrationInitials>
     *       <Channels>
     *         <Channel number="1" name="A/D:1">
     *           <Description>A/D With Thermister</Description>
     *         </Channel>
     *       </Channels>
     *     </SensorConfiguration>
     *   </Configuration>
     *   <DataItems>
     *     <DataItem category="CONDITION" id="sensorc" 
     *       name="sensorc" type="SYSTEM" />
     *     <DataItem category="SAMPLE" id="senv" name="sensorc"
     *       type="VOLTAGE_DC" units="VOLT" subType="ACTUAL" />
     *   </DataItems>
     * </Sensor>
     * ~~~~
     * {: caption="Example of configuration data for Sensor"}  */
}
package Imports {
    package 'CSV Imports' {
        occurrence def PropertyMap {
            private attribute propertyName : ScalarValues::String;
            private attribute stereotypeName : ScalarValues::String;
            private columnIndex;
        }
        occurrence def ImportDescriptor {
            private attribute csvFileName : ScalarValues::String;
            private attribute elementTypeName : ScalarValues::String;
            private attribute packageName : ScalarValues::String;
            private attribute diagramTypeName : ScalarValues::String;
            private useFirstRowAsHeaders;
            private useFindOwnerByTagId;
            private attribute stereoTypeNames : ScalarValues::String;
            private attribute identifierName : ScalarValues::String;
            private attribute relationEndIdentifier : ScalarValues::String;
            private attribute propertyMapNames [*] : ScalarValues::String;
            private attribute fieldSeparator : ScalarValues::String;
        }
    }
    package 'Unit Imports' {
        package 'Basic Units' {
            package 'Basic Length';
            package 'Basic Mass';
            package 'Basic Area';
            package 'Basic Volume';
            package 'Basic Time';
            package 'Basic Electric Current';
            package 'Basic Thermodynamic Temperature';
            package 'Basic Amount of Substance';
            package 'Basic Luminous Intensity';
            package 'Basic Speed and Velocity';
            package 'Basic Acceleration';
            package 'Basic Mass Density';
            package 'Basic Electric Current Density';
            package 'Basic Amount of Substance Concentration';
            package 'Basic Magnetic Field Strength';
            package 'Basic Luminance';
        }
    }
}
package 'WIP: Use Cases' {
    package 'Machine Monitoring' {
        part def 'Manufacturing Equipment' {
            include use case : 'What is the Device Utilization?';
            include use case : 'Monitor Operational States' {
                subject ;
            }
        }
        requirement <monitoring_req> 'Machine Monitoring' {
            doc /* Requirements for Machine Monitoring Use Case*/
        }
        #ModelingMetadata::refinement dependency from 'Machine Monitoring' to 'Monitor Operational States';
        use case def 'What is the Device Utilization?';
        use case def 'Monitor Operational States' {
            subject ;
            actor : Actors::Operator;
            include use case : 'What is the Device Utilization?';
        }
    }
    package Actors {
        part def Operator;
    }
    package 'Power Source' {
        part def 'Manufacturing Equipment' {
            include use case : 'What is the active power source?';
            include use case : 'Look up the power source configuration.' {
                subject ;
            }
        }
        use case def 'What is the active power source?';
        use case def 'Look up the power source configuration.' {
            subject ;
            actor : Actors::Operator;
            include use case : 'What is the active power source?';
        }
        requirement <power_config_req> 'Power Configuration Lookup' {
            doc /* Requirements for Power Configuration Lookup Use Case*/
        }
        #ModelingMetadata::refinement dependency from 'Power Configuration Lookup' to 'Look up the power source configuration.';
    }
}
doc 
/* ---
 *
 * The normative XMI is located at the following URL: [`MTConnectSysMLModel.xml`](./MTConnectSysMLModel.xml)
 *
 * ---
 *
 * This MTConnect model is normative and any content that is informative and/or is defined for descriptive purposes only has been either stereotyped as <<informative>> or documented as "Notes".
 *
 * ---
 *
 * {{term(AMT)}} owns the copyright in this MTConnect Specification or Material. {{term(AMT)}} grants to you a non-exclusive, non-transferable, revocable, non-sublicensable, fully-paid-up copyright license to reproduce, copy and redistribute this MTConnect Specification or Material, provided that you may only copy or redistribute the MTConnect Specification or Material in the form in which you received it, without modifications, and with all copyright notices and other notices and disclaimers contained in the MTConnect Specification or Material.
 *
 * If you intend to adopt or implement an MTConnect Specification or Material in a product, whether hardware, software or firmware, which complies with an MTConnect Specification, you shall agree to the MTConnect Specification Implementer License Agreement ("Implementer License") or to the MTConnect Intellectual Property Policy and Agreement ("IP Policy"'). The Implementer License and IP Policy each sets forth the license terms and other terms of use for MTConnect Implementers to adopt or implement the MTConnect Specifications, including certain license rights covering necessary patent claims for that purpose. These materials can be found at {{url(www.MTConnect.org)}}, or or by contacting {{url(mailto:info@MTConnect.org)}}. 
 *
 * MTConnect Institute and {{term(AMT)}} have no responsibility to identify patents, patent claims or patent applications which may relate to or be required to implement a Specification, or to determine the legal validity or scope of any such patent claims brought to their attention. Each MTConnect Implementer is responsible for securing its own licenses or rights to any patent or other intellectual property rights that may be necessary for such use, and neither {{term(AMT)}} nor MTConnect Institute have any obligation to secure any such rights.
 *
 * This Material and all MTConnect Specifications and Materials are provided "as is" and MTConnect Institute and {{term(AMT)}}, and each of their respective members, officers, affiliates, sponsors and agents, make no representation or warranty of any kind relating to these materials or to any implementation of the MTConnect Specifications or Materials in any product, including, without limitation, any expressed or implied warranty of noninfringement, merchantability, or fitness for particular purpose, or of the accuracy, reliability, or completeness of information contained herein. In no event shall MTConnect Institute or {{term(AMT)}} be liable to any user or implementer of MTConnect Specifications or Materials for the cost of procuring substitute goods or services, lost profits, loss of use, loss of data or any incidental, consequential, indirect, special or punitive damages or other direct damages, whether under contract, tort, warranty or otherwise, arising in any way out of access, use or inability to use the MTConnect Specification or other MTConnect Materials, whether or not they had advance notice of the possibility of such damage.*/
